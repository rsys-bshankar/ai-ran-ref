module o-ran-o1-EPD2U {
  yang-version 1.1;
  namespace "urn:o-ran:o-ran-o1-EPD2U";
  prefix "or-o1-EPD2U";

  import _3gpp-common-top { prefix top3gpp; }
  import _3gpp-common-managed-element { prefix me3gpp; }
  import _3gpp-common-ep-rp { prefix eprp3gpp; }
  import _3gpp-nr-nrm-gnbdufunction { prefix gnbdu3gpp; }
  import _3gpp-nr-nrm-ep { prefix ep3gpp; }
  import ietf-inet-types { prefix inet; }
  import _3gpp-common-yang-types { prefix types3gpp ; }
  import _3gpp-common-measurements { prefix meas3gpp; }

  organization "O-RAN Alliance";
  contact
    "www.o-ran.org";
  description
    "This module is for O-RAN Work Group 10 O1 Interface Specification for D2 Interface End Points
    Copyright 2026 the O-RAN Alliance.
    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.
    Redistribution and use in source and binary forms, with or without
    modification, are permitted provided that the following conditions are met:
    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision 2026-01-01 {
    description
      "version 1.0.0
      1) Initial version";
    reference "O-RAN.WG10.TS.O1NRM";
  }

  grouping EP_D2UGrp {
    description "Represents the EP_D2U IOC.";
    reference "O-RAN.WG10.TS.O1NRM";

    uses eprp3gpp:EP_Common {
      refine remoteAddress {
        config false;
        }
      }

    leaf localPortNumber {
      type inet:port-number;
      description "Port number used at local entity for establishing UDP connection for D2U interface";
    }

    leaf remotePortNumber {
      type inet:port-number;
      config false;
      description "Port number used at far end entity for establishing UDP connection for D2U interface";
    }
  }

  augment "/me3gpp:ManagedElement/gnbdu3gpp:GNBDUFunction" {
    if-feature ep3gpp:EPClassesUnderGNBDUFunction;
    description "EP_D2U is contained by GNBDUFunction.";

    list EP_D2U {
      key id;
      max-elements 255;
      description "Represents the local end point of the user plane
        interface (D2-U) between two O-DUs.";

      uses top3gpp:Top_Grp;

      container attributes {
        description "Attributes for managment aspects of D2-U transport parameters.";
        uses EP_D2UGrp;
      }
    }
  }
}
