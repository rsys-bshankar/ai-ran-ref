module o-ran-o1-managed-application {
  yang-version 1.1;
  namespace "urn:o-ran:o-ran-o1-managed-application";
  prefix "or-ma";

  import _3gpp-common-yang-types { prefix types3gpp; }

  organization "O-RAN Alliance";

  contact
    "www.o-ran.org";

  description
    "This Information Object Class (IOC) is provided for sub-classing only.
    It provides attribute(s) that are common to application IOCs

    Copyright 2025 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2025-07-02" {
    description
      "version 3.0.0

       1) Alignment to new YANG Conventions";

    reference "O-RAN.WG10.TS.O1NRM.0-R004-v04.00";
  }

  revision "2024-07-11" {
    description
      "version 2.0.0

       1) Referenced document changed";

    reference "O-RAN.WG10.O1NRM.0-R004-v01.00";
  }

  revision "2023-06-14" {
    description
      "version 1.0.0

      1) initial version.";

    reference "O-RAN.WG10.Information Model and Data Models.0-R003-v05.00";
  }

  grouping ManagedApplicationGrp {
    description "Represents the ManagedApplication IOC.";

    leaf applicationVersion {
      type string;
      config false;
      mandatory true;
      description "This attribute contains the application version.";
    }

    leaf applicationName {
      type string;
      mandatory true;
      description "This attribute contains the name (human readable) of the application.";
    }

    leaf hostDN {
      type types3gpp:DistinguishedName;
      config false;
      mandatory true;
      description
        "This attribute contains the DN of the hosting entity (e.g., NearRTRICFunction).
         Note: This attribute can be set only at creation time (equals isInvariant = true)";
    }
  }
}
