module o-ran-o1-subscription-control-subnetwork {
  yang-version 1.1;
  namespace "urn:o-ran:o-ran-o1-subscription-control-subnetwork";
  prefix "or-scsn";

  import _3gpp-common-subnetwork { prefix subnet3gpp; }
  import o-ran-o1-subscription-control { prefix oransctrl; }

  organization "O-RAN Alliance";

  contact
    "www.o-ran.org";

  description
    "This module is for supporting O1 aligned O-RAN subscription control for O-RAN defined notifications
    for subnetwork.

    Copyright 2025 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2025-07-02" {
    description
      "version 2.0.0

       1) Alignment to new YANG Conventions";

    reference "O-RAN.WG10.TS.O1NRM.0-R004-v04.00";
  }

  revision 2021-09-15 {
    description
      "Initial version";
    reference "O-RAN.WG5.MP.0-v01.00" ;
  }

  augment /subnet3gpp:SubNetwork {
    description
      "Augmentation of Sub network with O-RAN Subscription Control";
    uses oransctrl:OranSubscriptionControlWrapper;
  }
}
