module _3gpp-nr-nrm-gnbcuupfunction {
  yang-version 1.1;
  namespace "urn:3gpp:sa5:_3gpp-nr-nrm-gnbcuupfunction";
  prefix "gnbcuup3gpp";
    
  import _3gpp-common-yang-types { prefix types3gpp; }
  import _3gpp-common-yang-extensions { prefix yext3gpp; }
  import _3gpp-common-managed-function { prefix mf3gpp; }
  import _3gpp-common-managed-element { prefix me3gpp; }
  import _3gpp-common-top { prefix top3gpp; }
  import _3gpp-5g-common-yang-types { prefix types5g3gpp; }
  import _3gpp-5gc-nrm-configurable5qiset { prefix fiveqi3gpp; }

  organization "3GPP SA5";
  contact "https://www.3gpp.org/DynaReport/TSG-WG--S5--officials.htm?Itemid=464";
  description "Defines the YANG mapping of the GNBCUUPFunction Information
    Object Class (IOC) that is part of the NR Network Resource Model (NRM).
    Copyright 2026, 3GPP Organizational Partners (ARIB, ATIS, CCSA, ETSI, TSDSI, 
    TTA, TTC). All rights reserved.";
  reference "3GPP TS 28.541 5G Network Resource Model (NRM)";

  revision 2026-04-25 { reference CR-1703; }
  revision 2024-11-01 { reference CR-1405 ; } 
  revision 2024-05-24 { reference CR-1273 ; } 
  revision 2023-09-18 { reference CR-1043 ; } 
  revision 2023-04-26 { reference CR-0916; }
  revision 2022-07-28 { reference "CR-0770"; }
  revision 2020-11-05 { reference CR-0412 ; }
  revision 2020-08-06 { reference "CR-0333"; }
  revision 2020-08-03 { reference "CR-0321"; }
  revision 2020-06-03 { reference "CR-0286"; }
  revision 2020-05-28 { reference "CR-0318"; } 
  revision 2020-03-12 { reference "SP-200233 S5-201547"; }
  revision 2020-02-14 { reference S5-20XXXX ; }
  revision 2019-10-28 { reference S5-193518 ; }
  revision 2019-08-21 { reference "Initial revision"; }

  feature Configurable5QISetUnderGNBCUUPFunction {
    description "The Configurable5QISet shall be contained under
    GNBCUUPFunction";
  }

  grouping GNBCUUPFunctionGrp {
    description "Represents the GNBCUUPFunction IOC.";
    reference "3GPP TS 28.541";
    uses mf3gpp:ManagedFunctionGrp; 

    leaf gNBCUUPId {
      type uint64 {
        range "0..68719476735" ;
      }
      config false;
      mandatory true;
      yext3gpp:inVariant;
      description "Identifies the gNB-CU-UP at least within a gNB-CU-CP";
      reference "'gNB-CU-UP ID' in subclause 9.3.1.15 of 3GPP TS 38.463";
    }

    leaf gNBId {
      type uint32;
      mandatory true;
      description "Identifies a gNB within a PLMN. The gNB ID is part of the 
        NR Cell Identifier (NCI) of the gNB cells. ";
      reference "gNB Identifier (gNB ID) of subclause 8.2 of TS 38.300.
         Global gNB ID in subclause 9.3.1.6 of TS 38.413";
    }
    
    leaf gNBIdLength {
      mandatory true;
      type int32 { range "22..32"; }
      description "Indicates the number of bits for encoding the gNB Id.";
      reference "gNB Id in 3GPP TS 38.300, Global gNB ID in 3GPP TS 38.413";
    }
            
    list pLMNInfoList {
      description "The PLMNInfoList is a list of PLMNInfo data type. It 
        defines which PLMNs that can be served by the GNBCUUPFunction and 
        which S-NSSAIs can be supported by the GNBCUUPFunction for 
        corresponding PLMN in case of network slicing feature is supported";
      key "mcc mnc sd sst";
      uses types5g3gpp:PLMNInfo;
    }

    leaf isOnboardSatellite {
      type boolean;
      default false;
      config false;
      yext3gpp:inVariant;
      description "This attribute indicates whether the function is
      on board the satellite.";
    }
    leaf onboardSatelliteId {
      type string;
      config false;
      yext3gpp:inVariant;
      description "This attribute indicates the onboard satellite Id.
      It shall be formatted as a fixed 5-digit string, padding with
       leading digits '0' to complete a 5-digit length.";
    }
    
    leaf configurable5QISetRef {
      type types3gpp:DistinguishedName;
      description "DN of the Configurable5QISet that the GNBCUUPFunction 
        supports (is associated to).";
    }
    leaf dynamic5QISetRef {
      type types3gpp:DistinguishedName;
      description "DN of the Dynamic5QISet that the GNBCUUPFunction 
        supports (is associated to).";
    }
  }

  augment "/me3gpp:ManagedElement" {

    list GNBCUUPFunction {
      key id;
      description "Represents the logical function CU-UP of gNB or en-gNB.";
      reference "3GPP TS 28.541";
      uses top3gpp:Top_Grp;
      container attributes {    
        uses GNBCUUPFunctionGrp;
      }
      uses mf3gpp:ManagedFunctionContainedClasses;

      uses fiveqi3gpp:Configurable5QISetSubtree {
        if-feature Configurable5QISetUnderGNBCUUPFunction;
      }
    }
  }
}
