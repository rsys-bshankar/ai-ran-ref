module _3gpp-5gc-nrm-dccffunction {
  yang-version 1.1;
  namespace urn:3gpp:sa5:_3gpp-5gc-nrm-dccffunction;
  prefix dccf3gpp;

  import _3gpp-common-managed-function { prefix mf3gpp; }
  import _3gpp-common-managed-element { prefix me3gpp; }
  import _3gpp-common-yang-types { prefix types3gpp; }
  import _3gpp-5g-common-yang-types { prefix types5g3gpp; }
  import _3gpp-common-top { prefix top3gpp; }
  import _3gpp-5gc-nrm-managed-nfprofile { prefix mnfp3gpp; }
  import ietf-inet-types { prefix inet; }

  organization "3gpp SA5";
  contact
    "https://www.3gpp.org/DynaReport/TSG-WG--S5--officials.htm?Itemid=464";
  description "This IOC represents the DCCF function in 5GC.
    For more information about the DCCF, see TS 23.501.
    Copyright 2026, 3GPP Organizational Partners (ARIB, ATIS,
    CCSA, ETSI, TSDSI, TTA, TTC). All rights reserved.";
  reference "3GPP TS 28.541";

  revision 2026-04-25 { reference CR-1702; }

  grouping DccfInfoGrp {
    description "This data type represents the Specific
      data for the DCCF.
      (See clause 6.1.6.2.46 TS 29.510).";

    leaf-list servingNfTypeList {
      //optional support
      type types3gpp:NfType;
      description "This attribute represents the list of
        NF type(s) from which the DCCF NF can collect
        data. The absence of this attribute indicates
        that the DCCF can collect data from any NF
        type.";
    }

    leaf-list servingNfSetIdList {
      //optional support
      type string;
      description "This attribute represents the list of
        NF Set Id(s) from which the DCCF NF can collect
        data. The absence of this attribute indicates
        that the DCCF can collect data from any NF
        Set.";
    }

    list taiList {
      //optional support
      description "This attribute represents the list of
        TAIs the DCCF can serve. It may contain one or
        more non-3GPP access TAIs. The absence of both
        this attribute and the taiRangeList attribute
        indicates that the DCCF can be selected for any
        TAI in the serving network.";
      key idx;
      leaf idx { type uint32; }
      uses types3gpp:TaiGrp;
    }

    list taiRangeList {
      //optional support
      description "This attribute represents the range
        of TAIs the DCCF can serve. It may contain one
        or more non-3GPP access TAI ranges. The absence
        of both this attribute and the taiList attribute
        indicates that the DCCF can be selected for any
        TAI in the serving network.";
      key idx;
      leaf idx { type uint32; }
      uses types5g3gpp:TaiRangeGrp;
    }
  }

  grouping DCCFFunctionGrp {
    description "Represents the DCCFFunction IOC.";
    uses mf3gpp:ManagedFunctionGrp;

    list pLMNInfoList {
      description "It defines the PLMN(s) of a Network
        Function.";
      key "mcc mnc sd sst";
      min-elements 1;
      uses types5g3gpp:PLMNInfo;
    }

    leaf sBIFQDN {
      description "The FQDN of the registered NF instance
        in the service-based interface.";
      type inet:domain-name;
    }

    leaf-list cNSIIdList {
      //optional support
      description "NSI ID. NSI ID is an identifier for
        identifying the Core Network part of a Network
        Slice instance when multiple Network Slice
        instances of the same Network Slice are deployed,
        and there is a need to differentiate between them
        in the 5GC";
        reference " see clause 3.1 of TS 23.501 and
        subclause 6.1.6.2.7 of 3GPP TS 29.531.";
      type string;
    }

    list managedNFProfile {
      key idx;
      leaf idx { type uint32; }
      min-elements 1;
      max-elements 1;
      description "Profile definition of a Managed NF";
      reference "(See TS 23.501).";
      uses mnfp3gpp:ManagedNFProfileGrp;
    }

    list commModelList {
      min-elements 1;
      key "groupId";
      description "Specifies a list of commModel. It can
        be used by NF and NF services to interact with
        each other in 5G Core network.";
      reference "3GPP TS 23.501";
      uses types5g3gpp:CommModel;
    }

    list dccfInfo {
      //optional support
      description "This attribute represents information
        of a DCCF NF Instance.";
      max-elements 1;
      key idx;
      leaf idx { type uint32; }
      uses DccfInfoGrp;
    }
  }

  augment "/me3gpp:ManagedElement" {
    list DCCFFunction {
      description "5G Core DCCF Function";
      reference "3GPP TS 28.541";
      key id;
      uses top3gpp:Top_Grp;
      container attributes {
        uses DCCFFunctionGrp;
      }
      uses mf3gpp:ManagedFunctionContainedClasses;
    }
  }
}
