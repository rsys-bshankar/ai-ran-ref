module _3gpp-5gc-nrm-nssaaffunction {
  yang-version 1.1;
  namespace urn:3gpp:sa5:_3gpp-5gc-nrm-nssaaffunction;
  prefix nssaaf3gpp;

  import _3gpp-common-managed-function { prefix mf3gpp; }
  import _3gpp-common-managed-element { prefix me3gpp; }
  import _3gpp-5g-common-yang-types { prefix types5g3gpp; }
  import _3gpp-common-top { prefix top3gpp; }
  import _3gpp-5gc-nrm-managed-nfprofile { prefix mnfp3gpp; }
  import ietf-inet-types { prefix inet; }

  organization "3gpp SA5";
  contact
    "https://www.3gpp.org/DynaReport/TSG-WG--S5--officials.htm?Itemid=464";
  description "This IOC represents the NSSAAF function in 5GC.
    For more information about the NSSAAF, see TS 23.501.
    Copyright 2026, 3GPP Organizational Partners (ARIB, ATIS,
    CCSA, ETSI, TSDSI, TTA, TTC). All rights reserved.";
  reference "3GPP TS 28.541";

  revision 2026-03-25 { reference "CR-"; }

  grouping NssaafInfoGrp {
    description "This data type represents the information
      of a NSSAAF NF Instance.
      (See clause 6.1.6.2.104 TS 29.510).";

    list supiRanges {
      description "List of ranges of SUPIs that can be
        served by the NSSAAF instance.";
      key idx;
      leaf idx { type uint32; }
      uses types5g3gpp:SupiRangeGrp;
    }

    list internalGroupIdentifiersRanges {
      description "List of ranges of Internal Group
        Identifiers that can be served by the NSSAAF
        instance. If not provided, it does not imply
        that the NSSAAF supports all internal groups.";
      key idx;
      leaf idx { type uint32; }
      uses types5g3gpp:InternalGroupIdRangeGrp;
    }
  }

  grouping NSSAAFFunctionGrp {
    description "Represents the NSSAAFFunction IOC.";
    uses mf3gpp:ManagedFunctionGrp;

    list pLMNInfoList {
      description "It defines the PLMN(s) of a Network
        Function.";
      key "mcc mnc sd sst";
      min-elements 1;
      uses types5g3gpp:PLMNInfo;
    }

    leaf sBIFQDN {
      description "The FQDN of the registered NF instance
        in the service-based interface.";
      type inet:domain-name;
    }

    leaf-list cNSIIdList {
      description "NSI ID. NSI ID is an identifier for
        identifying the Core Network part of a Network
        Slice instance when multiple Network Slice
        instances of the same Network Slice are deployed,
        and there is a need to differentiate between them
        in the 5GC, see clause 3.1 of TS 23.501 and
        subclause 6.1.6.2.7 of 3GPP TS 29.531.";
      type string;
    }

    list managedNFProfile {
      key idx;
      leaf idx { type uint32; }
      min-elements 1;
      max-elements 1;
      description "Profile definition of a Managed NF
        (See TS 23.501).";
      uses mnfp3gpp:ManagedNFProfileGrp;
    }

    list commModelList {
      min-elements 1;
      key "groupId";
      description "Specifies a list of commModel. It can
        be used by NF and NF services to interact with
        each other in 5G Core network.";
      reference "3GPP TS 23.501";
      uses types5g3gpp:CommModel;
    }

    list nssaafInfo {
      description "This attribute represents information
        of a NSSAAF NF Instance.";
      max-elements 1;
      key idx;
      leaf idx { type uint32; }
      uses NssaafInfoGrp;
    }
  }

  augment "/me3gpp:ManagedElement" {
    list NSSAAFFunction {
      description "5G Core NSSAAF Function";
      reference "3GPP TS 28.541";
      key id;
      uses top3gpp:Top_Grp;
      container attributes {
        uses NSSAAFFunctionGrp;
      }
      uses mf3gpp:ManagedFunctionContainedClasses;
    }
  }
}
