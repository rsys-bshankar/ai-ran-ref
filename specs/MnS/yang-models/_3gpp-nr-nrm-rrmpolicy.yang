module _3gpp-nr-nrm-rrmpolicy {
  yang-version 1.1;
  namespace "urn:3gpp:sa5:_3gpp-nr-nrm-rrmpolicy";
  prefix "rrmpolicy3gpp";

  import _3gpp-5g-common-yang-types { prefix types5g3gpp; }
  import _3gpp-common-top { prefix top3gpp; }
  import _3gpp-common-managed-element { prefix me3gpp; }
  import _3gpp-nr-nrm-nrcellcu { prefix nrcellcu3gpp ; }
  import _3gpp-nr-nrm-nrcelldu { prefix nrcelldu3gpp ; }
  import _3gpp-nr-nrm-gnbcucpfunction { prefix gnbcucp3gpp ; }
  import _3gpp-nr-nrm-gnbcuupfunction { prefix gnbcuup3gpp ; }
  import _3gpp-nr-nrm-gnbdufunction { prefix gnbdu3gpp ; }

  organization "3GPP SA5";
  contact "https://www.3gpp.org/DynaReport/TSG-WG--S5--officials.htm?Itemid=464";
  description "Defines the YANG mapping of the RRMPolicy abstract class that
    is part of the NR Network Resource Model (NRM).
    Copyright 2023, 3GPP Organizational Partners (ARIB, ATIS, CCSA, ETSI, TSDSI,
    TTA, TTC). All rights reserved.";
  reference "3GPP TS 28.541 5G Network Resource Model (NRM)";

  revision 2023-09-19 { reference CR-1043 ; } //date updated; it was already used in R18
  revision 2022-07-28 { reference "CR-0770"; }
  revision 2020-11-05 { reference CR-0412 ; }
  revision 2020-04-28 { reference "CR0285"; }
  revision 2020-02-14 { reference "Initial revision"; }

  grouping RRMPolicyMemberGrp {
    description "This data type represents an RRM Policy member that will be
      part of a rRMPolicyMemberList. A RRMPolicyMember is defined by its
      pLMNId and sNSSAI (S-NSSAI).
      The members in a rRMPolicyMemberList are assigned a specific amount of
      RRM resources based on settings in RRMPolicy.";

    uses types5g3gpp:PLMNInfo;
  }

  grouping RRMPolicy_Grp {
    description "This IOC represents the properties of an abstract RRMPolicy
      . The RRMPolicy_ IOC needs to be subclassed to be instantiated.
      It defines two attributes apart from those inherited from Top IOC, the
      resourceType attribute defines type of resource (PRB, RRC
      connected users, DRB usage etc.) and the rRMPolicyMemberList attribute
      defines the RRMPolicyMember(s)that are subject to this policy.
      An RRM resource (defined in resourceType
      attribute) is located in NRCellDU, NRCellCU, GNBDUFunction,
      GNBCUCPFunction or in GNBCUUPFunction. The RRMPolicyRatio IOC is one
      realization of a RRMPolicy_ IOC. This RRM framework allows adding new
      policies, both standardized (like RRMPolicyRatio) or as vendor specific,
      by inheriting from the abstract RRMPolicy_ IOC.";

    leaf resourceType {
      description "The resourceType attribute defines type of resource (PRB,
        RRC connected users, DRB usage etc.) that is subject to policy.
       Valid values are 'PRB', 'PRB_UL', 'PRB_DL', 'RRC' or 'DRB'";
      mandatory true;
      type enumeration {
        enum PRB;
        enum PRB_UL;
        enum PRB_DL;
        enum RRC;
        enum DRB;
      }
    }

    list rRMPolicyMemberList{
      description "It represents the list of RRMPolicyMember (s) that the
        managed object is supporting. A RRMPolicyMember <<dataType>> include
        the PLMNId <<dataType>> and S-NSSAI <<dataType>>." ;
      min-elements 1;
      key "mcc mnc sd sst";
      uses RRMPolicyMemberGrp;
    }
  } // grouping

  grouping RRMPolicyRatioGrp {
    description "Represents the RRMPolicyRatio concrete IOC.";

    uses RRMPolicy_Grp;    // Inherits RRMPolicy_

    leaf rRMPolicyMaxRatio {
      description " This attribute specifies the maximum percentage of radio
       resource that can be used by the associated rRMPolicyMemberList.
       The maximum percentage of radio resource include at least one of
       the shared resources, prioritized resources and dedicated resources.
       The sum of the rRMPolicyMaxRatio values assigned to all RRMPolicyRatio(s)
       name-contained by same ManagedEntity can be greater that 100.";
      default 100;
      type uint8 { range "0..100"; }
      units percent;
    }

    leaf rRMPolicyMinRatio {
      description " This attribute specifies the minimum percentage of radio
        resources that can be used by the associated rRMPolicyMemberList.
        The minimum percentage of radio resources including at least one of
        prioritized resources and dedicated resources. The sum of the
        rRMPolicyMinRatio values assigned to all RRM PolicyRatio(s)
        name-contained by same ManagedEntity shall be less or equal 100.";
      default 0;
      type uint8 { range "0..100"; }
      units percent;
    }

    leaf rRMPolicyDedicatedRatio {
      description " This attribute specifies the percentage of radio resource
        that dedicatedly used by the associated rRMPolicyMemberList. The sum of
        the rRMPolicyDeidctaedRatio values assigned to all RRMPolicyRatio(s)
        name-contained by same ManagedEntity shall be less or equal 100. ";
      default 0;
      type uint8 { range "0..100"; }
      units percent;
      }
    }

  grouping RRMPolicySubtree {
    description "Contains RrmPolicy related classes.
      Should be used in all classes (or classes inheriting from)
      - NRCellCU, NRCellDU, GNBCUUPFunction, GNBCUCPFunction, GNBDUFunction

      If some YAM wants to augment these classes/list/groupings they must
      augment all user classes!";

    list RRMPolicyRatio {
      description "This IOC represents the properties of RRMPolicyRatio.
        RRMPolicyRatio is one realization of abstract RRMPolicy_ IOC.
        RRMPolicyRatio has three attributes, apart from those inherited
        (DN, resourceType, rRMPolicyMemberList).

        Structure of RRMPolicyRatio includes in order: Dedicated Resources,
        Prioritized Resources, Shared Resources, etc.

        - The attribute rRMPolicyMaxRatio defines the maximum resource usage
        quota for the associated rRMPolicyMemberList, including at least one of
        shared resources, prioritized resources and dedicated resources. The
        sum of the 'rRMPolicyMaxRatio' values assigned to all RRMPolicyRatio(s)
        name-contained by same MangedEntity can be greater than 100.
        - The attribute rRMPolicyMinRatio defines the minimum resource usage
        quota for the associated RRMPolicyMemberList, including at least one
        of prioritized resources and dedicated resources, which means the
        resources quota that need to be guaranteed for use by the associated
        rRMPolicyMemberList. The sum of the 'rRMPolicyMinRatio' values assigned
        to all RRMPolicyRatio(s) name-contained by same MangedEntity shall be
        less or equal 100.
        - The attribute rRMPolicyDedicatedRatio defines the dedicated resource
        usage quota for the RRMPolicyMemberList, including dedicated resources.
        The sum of the 'rRMPolicyDedicatedRatio' values assigned to all
        RRMPolicyRatio(s) name-contained by same MangedEntity shall be less
        or equal 100.

        The following are the definition for above mentioned three resource
        categories:
        - Shared resources: means the resources that are shared with other
        rRMPolicyMemberList(s) (i.e. the rRMPolicyMemberList(s) defined in
        RRMPolicyRatio(s) name-contained by the same ManagedEntity). The shared
        resources are not guaranteed for use by the associated
        rRMPolicyMemberList. The shared resources quota is represented by
        [rRMPolicyMaxRatio-rRMPolicyMinRatio].
        - Priortized resources: means the resources are preferentially used by
        the associated RRMPolicyMemberList. These resources are guaranteed for
        use by the associated RRMPolicyMemberList when it needs to use them.
        When not used, these resources may be used by other
        rRMPolicyMemberList(s) (i.e. the rRMPolicyMemberList(s) defined in
        RRMPolicyRatio(s) name-contained by the same ManagedEntity).
        The prioritized resources quota is represented by
        [rRMPolicyMinRatio-rRMPolicyDedicatedRatio]
        - Dedicated resources: means the resources are dedicated for use by
        the associated RRMPolicyMemberList. These resources can not be shared
        even if the associated RRMPolicyMember does not use them. The Dedicated
        resources quota is represented by [rRMPolicyDedicatedRatio].";
      key id;
      uses top3gpp:Top_Grp;
      container attributes {
        uses RRMPolicyRatioGrp;
      }
    }
  }

  augment "/me3gpp:ManagedElement/gnbcucp3gpp:GNBCUCPFunction/" +
      "nrcellcu3gpp:NRCellCU" {
    uses RRMPolicySubtree;
  }

  augment "/me3gpp:ManagedElement/gnbdu3gpp:GNBDUFunction/" +
      "nrcelldu3gpp:NRCellDU" {
    uses RRMPolicySubtree;
  }

  augment "/me3gpp:ManagedElement/gnbcuup3gpp:GNBCUUPFunction" {
    uses RRMPolicySubtree;
  }

  augment "/me3gpp:ManagedElement/gnbcucp3gpp:GNBCUCPFunction" {
    uses RRMPolicySubtree;
  }

  augment "/me3gpp:ManagedElement/gnbdu3gpp:GNBDUFunction" {
    uses RRMPolicySubtree;
  }

}
