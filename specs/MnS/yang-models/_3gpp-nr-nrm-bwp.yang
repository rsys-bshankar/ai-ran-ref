module _3gpp-nr-nrm-bwp {
  yang-version 1.1;
  namespace "urn:3gpp:sa5:_3gpp-nr-nrm-bwp";
  prefix "bwp3gpp";

  import _3gpp-common-managed-element { prefix me3gpp; }
  import _3gpp-common-managed-function { prefix mf3gpp; }
  import _3gpp-common-top { prefix top3gpp; }
  import _3gpp-nr-nrm-gnbdufunction { prefix gnbdu3gpp; }

  organization "3GPP SA5";
  contact "https://www.3gpp.org/DynaReport/TSG-WG--S5--officials.htm?Itemid=464";
  description "Defines the YANG mapping of the BWP Information Object Class
    (IOC) that is part of the NR Network Resource Model (NRM).
    Copyright 2023, 3GPP Organizational Partners (ARIB, ATIS, CCSA, ETSI, TSDSI, 
    TTA, TTC). All rights reserved.";
  reference "3GPP TS 28.541 5G Network Resource Model (NRM)";

  revision 2023-09-18 { reference CR-1043 ; } 
  revision 2020-11-17 { reference CR-0410 ; }
  revision 2019-10-28 { reference S5-193518 ; }
  revision 2019-06-17 { reference "Initial revision"; }

  typedef CyclicPrefix {
    type enumeration {
      enum NORMAL;
      enum EXTENDED;
    }
  }

  typedef BwpContext {
    type enumeration {
      enum DL;
      enum UL;
      enum SUL;
    }
  }
  typedef IsInitialBwp {
    type enumeration {
      enum INITIAL;
      enum OTHER;
    }
  }

  grouping BWPGrp {
    description "Represents the BWP IOC.";
    reference "3GPP TS 28.541";
    uses mf3gpp:ManagedFunctionGrp;

    leaf bwpContext {
      description "Identifies whether the object is used for downlink, uplink
        or supplementary uplink.";
      mandatory true;
      type BwpContext;
    }

    leaf isInitialBwp {
      description "Identifies whether the object is used for initial or other
        BWP.";
      mandatory true;
      type IsInitialBwp;
    }

    leaf subCarrierSpacing {
      description "Subcarrier spacing configuration for a BWP.";
      reference "3GPP TS 38.104";
      mandatory true;
      type uint32 { range "15 | 30 | 60 | 120"; }
      units kHz;
    }

    leaf cyclicPrefix {
      description "Cyclic prefix, which may be normal or extended."; 
      reference "3GPP TS 38.211";
      mandatory true;
      type CyclicPrefix;
    }

    leaf startRB {
      description "Offset in common resource blocks to common resource block 0
        for the applicable subcarrier spacing for a BWP.";
      reference "N_BWP_start in 3GPP TS 38.211";
      mandatory true;
      type uint32;
    }

    leaf numberOfRBs {
      description "Number of physical resource blocks for a BWP.";
      reference "N_BWP_size in 3GPP TS 38.211";
      mandatory true;
      type uint32;
    }
  }

  augment "/me3gpp:ManagedElement/gnbdu3gpp:GNBDUFunction" {

    list BWP {
      description "Represents a bandwidth part (BWP).";
      key id;
      uses top3gpp:Top_Grp;
      container attributes {    
        uses BWPGrp;
      }
      uses mf3gpp:ManagedFunctionContainedClasses;
    }
  }
}
