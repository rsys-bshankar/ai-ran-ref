module _3gpp-5gc-nrm-aanffunction {
  yang-version 1.1;
  namespace urn:3gpp:sa5:_3gpp-5gc-nrm-aanffunction;
  prefix aanf3gpp;

  import _3gpp-common-managed-function { prefix mf3gpp; }
  import _3gpp-common-managed-element { prefix me3gpp; }
  import _3gpp-5g-common-yang-types { prefix types5g3gpp; }
  import _3gpp-common-top { prefix top3gpp; }
  import _3gpp-5gc-nrm-managed-nfprofile { prefix mnfp3gpp; }
  import ietf-inet-types { prefix inet; }

  organization "3gpp SA5";
  contact
    "https://www.3gpp.org/DynaReport/TSG-WG--S5--officials.htm?Itemid=464";
  description "This IOC represents the AAnF function in 5GC.
    For more information about the AANF, see TS 33.535.
    Copyright 2026, 3GPP Organizational Partners (ARIB, ATIS,
    CCSA, ETSI, TSDSI, TTA, TTC). All rights reserved.";
  reference "3GPP TS 28.541";

  revision 2026-04-25 { reference CR-1702; }

  grouping AanfInfoGrp {
    description "This data type represents the Specific
      data for the AAnF.
      (See clause 6.1.6.2.73 TS 29.510).";

    leaf-list routingIndicators {
      description "This attribute represents the List of
        Routing Indicators supported by the AAnf
        instance. If not provided, the AAnf can serve
        any Routing Indicator.";
        //optional
      type string {
        pattern '[0-9]{1,4}';
      }
    }
  }

  grouping AANFFunctionGrp {
    description "Represents the AANFFunction IOC.";
    uses mf3gpp:ManagedFunctionGrp;

    list pLMNInfoList {
      description "It defines the PLMN(s) of a Network
        Function.";
      key "mcc mnc sd sst";
      min-elements 1;
      uses types5g3gpp:PLMNInfo;
    }

    leaf sBIFQDN {
      description "The FQDN of the registered NF instance
        in the service-based interface.";
      type inet:domain-name;
    }

    list managedNFProfile {
      key idx;
      leaf idx { type uint32; }
      min-elements 1;
      max-elements 1;
      description "Profile definition of a Managed NF
        (See TS 23.501).";
      uses mnfp3gpp:ManagedNFProfileGrp;
    }

    list commModelList {
      min-elements 1;
      key "groupId";
      description "Specifies a list of commModel. It can
        be used by NF and NF services to interact with
        each other in 5G Core network.";
      reference "3GPP TS 23.501";
      uses types5g3gpp:CommModel;
    }

    list aanfInfo {
      description "This attribute represents information
        of an AAnF NF Instance.";
        //optional
      max-elements 1;
      key idx;
      leaf idx { type uint32; }
      uses AanfInfoGrp;
    }
  }

  augment "/me3gpp:ManagedElement" {
    list AANFFunction {
      description "5G Core AAnF Function";
      reference "3GPP TS 28.541";
      key id;
      uses top3gpp:Top_Grp;
      container attributes {
        uses AANFFunctionGrp;
      }
      uses mf3gpp:ManagedFunctionContainedClasses;
    }
  }
}
