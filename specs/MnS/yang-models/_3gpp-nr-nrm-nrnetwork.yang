module _3gpp-nr-nrm-nrnetwork {
  yang-version 1.1;
  namespace "urn:3gpp:sa5:_3gpp-nr-nrm-nrnetwork";
  prefix "nrnet3gpp";

  import _3gpp-common-managed-element { prefix me3gpp; }
  import _3gpp-nr-nrm-gnbcucpfunction { prefix gnbcucp3gpp; }
  import _3gpp-common-top { prefix top3gpp; }

  organization "3GPP SA5";
  contact "https://www.3gpp.org/DynaReport/TSG-WG--S5--officials.htm?Itemid=464";
  description "Defines the YANG mapping of the NRNetwork Information Object
    Class (IOC) that is part of the NR Network Resource Model (NRM).
    Copyright 2025, 3GPP Organizational Partners (ARIB, ATIS, CCSA, ETSI, TSDSI, 
    TTA, TTC). All rights reserved.";
  reference "3GPP TS 28.541 5G Network Resource Model (NRM)";

  revision 2025-04-25 { reference "CR-1526 CR-1527" ; } // common r17, r18 
  revision 2023-09-18 { reference CR-1043 ; } 
  revision 2019-06-17 { reference "Initial revision"; }

  grouping NRNetworkGrp {
    description "Represents the NRNetwork IOC.
      Contains no additiona attributes.";
  }

  augment /me3gpp:ManagedElement/gnbcucp3gpp:GNBCUCPFunction {
    list NRNetwork {
      description "Represents a set of NR frequencies and external NR entities 
        (e.g. ExternalGNBCUCPFunction). This is used to differentiate these
        entities and frequencies from those in EUTRAN.";
      key id;
      uses top3gpp:Top_Grp;
      container attributes {
        uses NRNetworkGrp;
      }
    }
  }
}
