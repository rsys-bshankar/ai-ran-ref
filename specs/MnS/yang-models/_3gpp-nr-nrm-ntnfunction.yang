module _3gpp-nr-nrm-ntnfunction {
  yang-version 1.1;
  
  namespace urn:3gpp:sa5:_3gpp-nr-nrm-ntnfunction;
  prefix ntn3gpp;
  
  import _3gpp-common-top { prefix top3gpp; }
  import _3gpp-5g-common-yang-types { prefix types5g3gpp; }
  import ietf-yang-types { prefix yang; }
  import _3gpp-common-managed-element { prefix me3gpp; }
  import _3gpp-common-subnetwork { prefix subnet3gpp; }
  import _3gpp-common-yang-types { prefix types3gpp; }
  
  organization "3gpp SA5";
  contact "https://www.3gpp.org/DynaReport/TSG-WG--S5--officials.htm?Itemid=464";
  description "Implements support the C-SON function of Capacity and 
    Coverage optimization .
    Copyright 2026, 3GPP Organizational Partners (ARIB, ATIS, CCSA, ETSI, TSDSI, 
    TTA, TTC). All rights reserved.";
  reference "3GPP TS 28.541";
  
  revision 2026-05-07 { reference CR-1717; }
  revision 2026-02-02 { reference "CR-1682 CR-1683"; } //Common in r19, r20
  revision 2025-03-27 { reference CR-1512; }
  revision 2025-02-17 { reference CR-1479 ; }
  revision 2024-05-24 { reference CR-1273 ; } 

  
  feature NTNFunctionUnderSubNetwork {
    description "The NTNFunction shall be contained under SubNetwork"; 
  }
 
  feature NTNFunctionUnderManagedElement {
    description "The NTNFunction shall be contained under ManagedElement"; 
  }
  
  grouping PositionVelocityGrp {
    description "This data type defines configuration parameters to support 
      satellite position and velocity state";
      
    leaf positionX {
      type uint32 {
        range 0..604800;
      }
      default 0;
      units meter;
      description "X, Y, Z coordinate of satellite position state vector 
        in ECEF. Unit is meter. 
        Step of 1.3 m. Actual value = field value * 1.3.";
    }
    
    leaf positionY {
      type uint32 {
        range 0..604800;
      }
      default 0;
      units meter;
      description "X, Y, Z coordinate of satellite position state vector 
        in ECEF. Unit is meter. 
        Step of 1.3 m. Actual value = field value * 1.3.";
    }
    
    leaf positionZ {
      type uint32 {
        range 0..604800;
      }
      default 0;
      units meter;
      description "X, Y, Z coordinate of satellite position state vector 
        in ECEF. Unit is meter. 
        Step of 1.3 m. Actual value = field value * 1.3.";
    }
    
    leaf velocityVX {
      type int32 {
        range -131072..131071;
      }
      default 0;
      units meter/second;
      description "X, Y, Z coordinate of satellite velocity state vector 
        in ECEF. 
        Step of 0.06 m/s. Actual value = field value * 0.06.";
    }
    
    leaf velocityVY {
      type int32 {
        range -131072..131071;
      }
      default 0;
      units meter/second;
      description "X, Y, Z coordinate of satellite velocity state vector 
        in ECEF. 
        Step of 0.06 m/s. Actual value = field value * 0.06.";
    }
    
    leaf velocityVZ {
      type int32 {
        range -131072..131071;
      }
      default 0;
      units meter/second;
      description "X, Y, Z coordinate of satellite velocity state vector 
        in ECEF. 
        Step of 0.06 m/s. Actual value = field value * 0.06.";
    }
  }
    
  grouping OrbitalGrp {
    description "This data type defines configuration parameters of orbital 
      trajectory information to support satellite access.";
      
    leaf semiMajorAxis {
      type uint64 {
        range 0..8589934591;
      }
      default 0;
      units meter;
      description "Satellite orbital parameter: semi major axis alpha. 
        Step of 4.249 * 10**-3 m. 
        Actual value = 6500000 + field value * (4.249 * 10**-3).";
    }
    
    leaf eccentricity {
      type int32 {
        range -524288..524287;
      }
      default 0;
      description "Satellite orbital parameter: eccentricity e.
        Step 1.431 * 10**-8. 
        Actual value = field value * (1.431 * 10**-8).";
    }
    
    leaf periapsis {
      type uint32 {
        range 0..16777215;
      }
      default 0;
      units radian;
      description "Satellite orbital parameter: argument of periapsis omega. 
        Step of 2.341* 10**-8 rad. 
        Actual value = field value * (2.341* 10**-8).";
    }
    
    leaf longitude {
      type uint32 {
        range 0..2097151;
      }
      default 0;                
      units radian;
      description "Satellite orbital parameter: longitude of ascending node 
        omega. 
        Step of 2.341* 10**-8 rad.
        Actual value = field value * (2.341* 10**-8).";
    }
    
    leaf inclination {
      type int32 {
        range -524288..524287;
      }
      default 0;
      units radian;
      description "Satellite orbital parameter: inclination i. 
        Step of 2.341* 10**-8 rad. 
        Actual value = field value * (2.341* 10**-8).";
    }
    
    leaf meanAnomaly {
      type uint32 {
        range 0..16777215;
      }
      default 0;
      units radian;
      description "Satellite orbital parameter: Mean anomaly M at epoch time. 
        Step of 2.341* 10**-8 rad. 
        Actual value = field value * (2.341* 10**-8).";
    }
  }
    
  grouping EphemerisGrp {
    description "This data type represents the satellite ephemeris related 
      information. The ephemeris data format may be expressed either in 
      format of position and velocity state vector or in format of orbital 
      parameters.";
      
    leaf satelliteId {
      type string {
        pattern "00([01][0-9][0-9])|(2[0-4][0-9]|(25[0-5]))";
      }
      description "This attribute indicates satellite Id.number. 
        It shall be formatted as a fixed 5-digit string, padding with 
        leading digits '0' to complete a 5-digit length.
        allowedValues: 00000..00255";
    }
    
    leaf epochTime {
      type yang:date-and-time;
      description "It defines the ephemeris reference time.";
    }
    
    choice positionVelocity-or-orbital {
      list positionVelocity {
        description "It indicates ephemeris is in format of NTN payload 
          position and velocity state vectors.";
        max-elements 1;
        key idx;
        leaf idx { type uint32; }
        uses PositionVelocityGrp;
      }
      
      list orbital {
        description "It indicates ephemeris is in orbital parameter ephemeris 
          format.";
        max-elements 1;
        key idx;
        leaf idx { type uint32; }
        uses OrbitalGrp;
      }
    }
  }
   
  grouping EphemerisInfoSetGrp {
    description "Represents the EphemerisInfoSet IOC";
    
    list EphemerisInfos {
      description "This is the list of Ephemeris related information.";
      min-elements 1;
      key idx;
      leaf idx { type uint32; }
      uses EphemerisGrp;
    }
  }
  
  grouping NTNEntityConfigGrp {
    description "The attribute nTNConfEntity specifies an NTN related MOI.
      The attribute nTNConfList optionally specifies configuration 
      updates to be applied to the nTNConfEntity.  If no updates are provided
      the value of nTNConfEntity is used without modification.";

    leaf nTNConfEntity {
      type types3gpp:DistinguishedName;
      description "Specifies the DN of a specific NTN related MOI.
        allowedValues:  DN of of the following MOIs:
        EP_NgC, NRCellCU, NRCellDU, NRSectorCarrier,
        SectorEquipmentFunction, NRCellRelation.";
    }

    list nTNConfigList {
      uses types3gpp:nameValuePair;
      key "name";
      description "Specifies the list of configuration parameters and values.
        The content of the attribute is a list of attributeName- attributeValue
        pairs.  AttributeValues may be complex types.";
    }    
  }

  grouping NTNTimeBasedConfigGrp {
    description "Define configuration to be applied during a specified time
      window.
      The attribute timeWindow specifies the time window during which the 
      specified configuration is applied.
      The attribute nTNEntityConfigList specifies configuration updates applied
      during the specified timeWindow.";

    list timeWindow {
      key idx;
      leaf idx { type uint32 ; }
      min-elements 1;
      max-elements 1;
      uses types3gpp:TimeWindowGrp;
      description "It defines the time window.";
    }

    list nTNEntityConfigList {
      key idx;
      leaf idx { type uint32 ; }
      uses NTNEntityConfigGrp;
      description "It contains a list of configuration
        updates to be applied to specified NTN entities.";
    }
  }
  
  grouping NTNFunctionGrp {
    description "Represents the NTNFunction IOC";
    
    list nTNpLMNInfoList {
      description "It defines which PLMNs that can be served by the NR NTN cell, 
        and which S-NSSAIs can be supported by the NR NTN cell for 
        corresponding PLMN in case of network slicing feature is supported. 
        The pLMNId of the first entry of the list is the PLMNId used to 
        construct the nCGI for the NR cell.";
      min-elements 1;
      ordered-by user;
      key idx;
      leaf idx { type uint32; }
      uses types5g3gpp:PLMNInfo;
    }
    
    leaf-list nTNTAClist {
      type types5g3gpp:NRTAC;
      min-elements 1;
      description "It is the list of Tracking Area Codes (either legacy TAC or 
        extended TAC) for NR NTN. 
        Legacy TAC and Extended TAC are defined in clause 9.3.3.10 of 
        TS 38.413.";
    }
  }
  
  grouping NTNFunctionSubtreeGrp {
    list NTNFunction {
      description "This IOC contains attributes to support the non-terrestrial 
        NR access.  This IOC contains instances of NTNTimeBasedConfig to support
        time-based configuration of the following NTN related entities:  
        EP_NgC, NRCellCU, NRCellDU, NRSectorCarrier, SectorEquipmentFunction, 
        and NRCellRelation.  The IP Configuration of the feeder links may be 
        configured via IP Autoconfiguration services [x] and/or configured via 
        instances of NTNTimeBasedConfig in anticipation of feeder link 
        switchovers.";
      key id;
      max-elements 1;
      uses top3gpp:Top_Grp;
      container attributes {
        uses NTNFunctionGrp;
      }

      list EphemerisInfoSet {
        description "This IOC represents the satellite ephemeris information 
          describing the orbital trajectory information or coordinates for the 
          NTN vehicles.";
        key id;
        uses top3gpp:Top_Grp;
        container attributes {
          uses EphemerisInfoSetGrp;
        }
      }

      list NTNTimeBasedConfig {
        description "This IOC represents the NTN time-based configuration.
        ";
        key id;
        uses top3gpp:Top_Grp;
        container attributes {
          uses NTNTimeBasedConfigGrp;
        }
      }
    }
  }
  
  augment "/subnet3gpp:SubNetwork" {
    if-feature NTNFunctionUnderSubNetwork;
    uses NTNFunctionSubtreeGrp;
  }
  
  augment "/me3gpp:ManagedElement" {
    if-feature NTNFunctionUnderManagedElement;
    uses NTNFunctionSubtreeGrp;
  }
}
