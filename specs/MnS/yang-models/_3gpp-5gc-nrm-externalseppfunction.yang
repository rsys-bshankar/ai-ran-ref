module _3gpp-5gc-nrm-externalseppfunction {
  yang-version 1.1;
  
  namespace urn:3gpp:sa5:_3gpp-5gc-nrm-extternalseppfunction;
  prefix extsepp3gpp;
  
  import _3gpp-common-managed-function { prefix mf3gpp; }
  import _3gpp-common-managed-element { prefix me3gpp; }
  import _3gpp-common-yang-types { prefix types3gpp; }
  import _3gpp-common-yang-extensions { prefix yext3gpp; }
  import _3gpp-common-top { prefix top3gpp; }
  import ietf-inet-types { prefix inet; }
  
  organization "3gpp SA5";
  contact "https://www.3gpp.org/DynaReport/TSG-WG--S5--officials.htm?Itemid=464";
  description "This IOC represents the external SEPP function which support 
    message filtering and policing on inter-PLMN control plane interface. 
    For more information about the SEPP, see 3GPP TS 23.501.
    Copyright 2023, 3GPP Organizational Partners (ARIB, ATIS, CCSA, ETSI, TSDSI, 
    TTA, TTC). All rights reserved.";
  reference "3GPP TS 28.541";
  
  revision 2023-09-18 { reference CR-1043 ; } 
  revision 2023-04-26 { reference CR-0916; }
  revision 2019-11-17 {reference "initial revision"; }

  grouping ExternalSEPPFunctionGrp {
    uses mf3gpp:ManagedFunctionGrp;
  
    container pLMNId {
      description "PLMN Identifiers of the sepp.
        The PLMN Identifier is composed of a Mobile Country Code (MCC) and a 
        Mobile Network Code (MNC).";
      yext3gpp:inVariant;
      uses types3gpp:PLMNId;
    }

    leaf sEPPId {
      type uint16;
      yext3gpp:inVariant;
    }    

    leaf fqdn {
      description "The domain name of the SEPP.";
      type inet:domain-name;
    }
  }
  
  augment "/me3gpp:ManagedElement" {
    list ExternalSEPPFunction {
      description "5G Core SEPP Function";
      reference "3GPP TS 28.541";
      key id;
      uses top3gpp:Top_Grp;
      container attributes {
        uses ExternalSEPPFunctionGrp;
      }
      uses mf3gpp:ManagedFunctionContainedClasses;
    }
  }
}
