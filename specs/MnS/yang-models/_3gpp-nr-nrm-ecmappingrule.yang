module _3gpp-nr-nrm-ecmappingrule {
  yang-version 1.1;
  namespace urn:3gpp:sa5:_3gpp-nr-nrm-ecmappingrule;
  prefix ecmap3gpp;

  import _3gpp-common-top { prefix top3gpp; }

  organization "3gpp SA5";
  contact "https://www.3gpp.org/DynaReport/TSG-WG--S5--officials.htm?Itemid=464";
  description "This IOC represents the unified mapping rule input to support
    Energy Cost Index Mapping when Energy Cost Reporting.
    Copyright 2026, 3GPP Organizational Partners (ARIB, ATIS, CCSA, ETSI, TSDSI,
    TTA, TTC). All rights reserved.";
  reference "3GPP TS 28.541";

  revision 2026-05-19 { reference "CR-1702 CR-1703" ; }  // common for R19, R20
  revision 2025-05-06 { reference "CR-1526 CR-1527" ; }  
  revision 2024-08-12 { reference "CR-1336 CR-1337"; }

  grouping NRECMappingRuleGrp {
    description "Represents the unified mapping rule to support Energy Cost Mapping
      when Energy Cost Reporting is supported.  Can be name-contained by SubNetwork
      or ManagedElement.  It applies to all ManagedEntity contained by the parent.";
    leaf ecMRInputMinimumValue {
      type uint32;
      mandatory true;
      description "The minimum value of to be applied
        for mapping from this attribute to the energy cost.";
    }

    leaf ecMRInputMaximumValue {
      type uint32;
      mandatory true;
      description "The maximum value of to be applied
        for mapping from this attribute to the energy cost.";
    }

    leaf ecTimeInterval {
      type uint32;
      mandatory true;
      description "Time interval (in seconds) that
        should be applied for collecting values of mapping
        rule attribute to be used for computing the energy cost.";
      units seconds;
    }
  }

  grouping NRECMappingRuleSubtree {
    description "Helps augmenting NRECMappingRule into multiple places.";
    list NRECMappingRule {
      description "Represents the unified mapping rule, applicable for the
        group of gNBs (within a certain area), for the calculation of the
        energy cost (see TS 34.423).

        NRECMappingRule can be name-contained by SubNetwork or ManagedElement.
        It applies to all ManagedEntity contained by the parent.";
      key id;
      uses top3gpp:Top_Grp;
      min-elements 1;
      max-elements 1;
      container attributes {
        uses NRECMappingRuleGrp;
      }
    }
  }
}
