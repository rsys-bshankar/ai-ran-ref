module _3gpp-5gc-nrm-udmfunction {
  yang-version 1.1;

  namespace urn:3gpp:sa5:_3gpp-5gc-nrm-udmfunction;
  prefix udm3gpp;

  import _3gpp-common-managed-function { prefix mf3gpp; }
  import _3gpp-common-managed-element { prefix me3gpp; }
  import ietf-inet-types { prefix inet; }
  import _3gpp-common-yang-types { prefix types3gpp; }
  import _3gpp-5g-common-yang-types { prefix types5g3gpp; }
  import _3gpp-common-top { prefix top3gpp; }
  import _3gpp-5gc-nrm-managed-nfprofile { prefix mnfp3gpp; }

  organization "3gpp SA5";
  contact "https://www.3gpp.org/DynaReport/TSG-WG--S5--officials.htm?Itemid=464";
  description "This IOC represents the UDM function in 5GC. For more
    information about the UDM, see 3GPP TS 23.501.
    Copyright 2026, 3GPP Organizational Partners (ARIB, ATIS, CCSA, ETSI, TSDSI,
    TTA, TTC). All rights reserved.";
  reference "3GPP TS 28.541";

  revision 2026-03-25 { reference CR-1694 ; }
  revision 2025-07-25 { reference CR-1558 ; }
  revision 2024-04-04 { reference CR-1139; }
  revision 2023-09-18 { reference CR-1043 ; }
  revision 2023-04-26 { reference CR-0916; }
  revision 2020-11-08 { reference CR-0412 ; }
  revision 2019-10-25 { reference "S5-194457 S5-195427 S5-193518"; }
  revision 2019-05-22 { reference "initial revision";}

    grouping InternalGroupIdRangeGrp {

      leaf start {
        description "It indicates first value identifying the start of an
        identity range, to be used when the range of identities can be
        represented as a consecutive numeric range.";
        type string;
      }

      leaf end{
        description "It indicates last value identifying the end of an
        identity range, to be used when the range of identities can be
        represented as a consecutive numeric range.";
        type string;
      }
      leaf pattern {
        description "It indicates pattern (regular expression according
        to the ECMA-262 dialect [75]) representing the set of identities
        belonging to this range. An identity value is considered part of
        the range if and only if the identity string fully matches the
        regular expression.";
        type string;
      }
    }
    grouping SuciInfoGrp {
      description "This data type represents SUCI information containing
        Routing Indicator and Home Network Public Key ID. (See TS 29.510)";

      leaf-list routingInds {
        type string;
        min-elements 1;
        description "It indicates served Routing Indicator (see TS 23.003,
          clause 2.2B). If not provided, the AUSF/UDM
          can serve any Routing Indicator.";
      }

      leaf-list hNwPubKeyIds  {
        type int64;
        min-elements 1;
        description "It indicating served Home Network Public Key
          (see TS 23.003, clause 2.2B). If not provided, the AUSF/UDM
          can serve any public key.";
      }
    }
    grouping UdmInfoGrp {

      leaf groupId {
        description "Identity of the UDM group that is served by the
        UDM instance. If not provided, the UDM instance does
         not pertain to any UDM group.";
        type string;
      }

      list supiRanges {
        description "List of ranges of SUPI's whose profile data is
        available in the UDM instance.";
        key idx;
        leaf idx { type uint32; }
        min-elements 1;
        uses types5g3gpp:SupiRangeGrp;
      }

      list gpsiRanges {
        description "List of ranges of GPSIs whose profile data is
        available in the UDM instance.";
        key idx;
        leaf idx { type uint32; }
        min-elements 1;
        uses types5g3gpp:IdentityRangeGrp;
      }

      list externalGroupIdentifiersRanges {
        description "List of ranges of external groups whose profile
         data is available in the UDM instance.";
        key idx;
        leaf idx { type uint32; }
        min-elements 1;
        uses types5g3gpp:IdentityRangeGrp;
      }

      leaf-list routingIndicators {
        description "List of Routing Indicator information that allows
         to route network signalling with SUCI
                     to the UDM instance. If not provided,
                     the UDM can serve any Routing Indicator.
                     Pattern: '^[0-9]{1,4}$'.";
        min-elements 1;
        type string;
      }

      list internalGroupIdentifiersRanges{
        description "It represents list of ranges of Internal Group
        Identifiers whose profile data is available in the UDM instance.
        If not provided, it does not imply that the UDM supports all
        internal groups.";
        key idx;
        leaf idx { type uint32; }
        uses InternalGroupIdRangeGrp;
      }
      list suciInfos {
        description "It represents list of SuciInfo. A SUCI that matches
        this information can be served by the UDM .A SUCI that matches
        all attributes of at least one entry in this array shall be
        considered as a match of this information";
        key idx;
        leaf idx { type uint32; }
        uses SuciInfoGrp;
      }
    }

  grouping UDMFuntionGrp {
    description "Represents the UDMFuntion IOC";
    uses mf3gpp:ManagedFunctionGrp;

    list pLMNIdList {
      description "List of at most six entries of PLMN Identifiers, but at
        least one (the primary PLMN Id).
        The PLMN Identifier is composed of a Mobile Country Code (MCC) and a
        Mobile Network Code (MNC).";

      min-elements 1;
      max-elements 6;
      key "mcc mnc";
      uses types3gpp:PLMNId;
    }

    leaf sBIFQDN {
      description "The FQDN of the registered NF instance in the service-based
        interface.";
      type inet:domain-name;
    }

    list sNSSAIList {
      description "List of S-NSSAIs the managed object is capable of supporting.
                   (Single Network Slice Selection Assistance Information)
                   An S-NSSAI has an SST (Slice/Service type) and an optional SD
                   (Slice Differentiator) field.";
      //optional support
      reference "3GPP TS 23.003";
      key "sd sst";
      uses types5g3gpp:SNssai;
    }

    list managedNFProfile {
      key idx;
      leaf idx { type uint32; }
      min-elements 1;
      max-elements 1;
      description "Profile definition of a Managed NF (See TS 23.501)";
      uses mnfp3gpp:ManagedNFProfileGrp;
    }

    list commModelList {
      min-elements 1;
      key "groupId";
      description "Specifies a list of commModel. It can be used by NF and
        NF services to interact with each other in 5G Core network ";
      reference "3GPP TS 23.501";
      uses types5g3gpp:CommModel;
    }

    list udmInfo {
      description "This attribute represents the information of an UDM NF
      Instance ";
      key idx;
      leaf idx { type uint32; }
      reference "TS 29.510 ";
      uses UdmInfoGrp;
    }

    leaf-list mdtUserConsentReqList {
      type enumeration {
        enum M1;
        enum M2;
        enum M3;
        enum M4;
        enum M5;
        enum M6;
        enum M7;
        enum M8;
        enum M9;
        enum MDT_UE_LOCATION;
      }
      description "represents a list of MDT measurement names that are
        subject to user consent at MDT activation.
        Any MDT measurement, whose name is not specified in this list, is not
        subject to user consent at MDT activation.";
    }
  }

  augment "/me3gpp:ManagedElement" {
    list UDMFunction {
      description "5G Core UDM Function";
      reference "3GPP TS 28.541";
      key id;
      uses top3gpp:Top_Grp;
      container attributes {
        uses UDMFuntionGrp;
      }
      uses mf3gpp:ManagedFunctionContainedClasses;
    }
  }
}
