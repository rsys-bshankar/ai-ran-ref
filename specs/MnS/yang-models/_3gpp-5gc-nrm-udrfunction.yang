module _3gpp-5gc-nrm-udrfunction {
  yang-version 1.1;

  namespace urn:3gpp:sa5:_3gpp-5gc-nrm-udrfunction;
  prefix udr3gpp;

  import _3gpp-common-managed-function { prefix mf3gpp; }
  import _3gpp-common-managed-element { prefix me3gpp; }
  import ietf-inet-types { prefix inet; }
  import _3gpp-common-yang-types { prefix types3gpp; }
  import _3gpp-common-top { prefix top3gpp; }
  import _3gpp-5g-common-yang-types { prefix types5g3gpp; }
  import _3gpp-5gc-nrm-managed-nfprofile { prefix mnfp3gpp; }

  organization "3gpp SA5";
  contact "https://www.3gpp.org/DynaReport/TSG-WG--S5--officials.htm?Itemid=464";
  description "This IOC represents the UDR function in 5GC. For more information
    about the UDR, see 3GPP TS 23.501.
    Copyright 2026, 3GPP Organizational Partners (ARIB, ATIS, CCSA, ETSI, TSDSI,
    TTA, TTC). All rights reserved.";
  reference "3GPP TS 28.541";

  revision 2026-03-25 { reference CR-1694 ; }
  revision 2025-07-25 { reference CR-1558 ; }
  revision 2023-09-18 { reference CR-1043 ; }
  revision 2023-04-26 { reference CR-0916; }
  revision 2020-11-08 { reference CR-0412 ; }
  revision 2019-10-25 { reference "S5-194457 S5-195427 S5-193518"; }

  revision 2019-05-22 {reference "initial revision"; }

    grouping UdrInfoGrp {

      leaf groupId {
        description "Identity of the UDR group that is served
         by the UDR instance.
          If not provided, the UDR instance does not pertain
           to any UDR group.";
        type string;
      }

      list supiRanges {
        description "List of ranges of SUPI's whose profile data
         is available in the UDR instance.";
        key idx;
        leaf idx { type uint32; }
        min-elements 1;
        uses types5g3gpp:SupiRangeGrp;
      }

      list gpsiRanges {
        description "List of ranges of GPSIs whose profile data is
         available in the UDR instance.";
        key idx;
        leaf idx { type uint32; }
        min-elements 1;
        uses types5g3gpp:IdentityRangeGrp;
      }

      list externalGroupIdentifiersRanges {
        description "List of ranges of external groups whose profile
         data is available in the UDR instance.";
        key idx;
        leaf idx { type uint32; }
        min-elements 1;
        uses types5g3gpp:IdentityRangeGrp;
      }

      leaf-list supportedDataSets {
        description "List of supported data sets in the UDR instance.
                     If not provided, the UDR supports all data sets.";
        min-elements 1;
        type DataSetId;
      }
    }
  grouping UDRFuntionGrp {
    description "Representse the UDRFuntion IOC";
    uses mf3gpp:ManagedFunctionGrp;

    list pLMNIdList {
      description "List of at most six entries of PLMN Identifiers, but at
        least one (the primary PLMN Id).
        The PLMN Identifier is composed of a Mobile Country Code (MCC) and a
        Mobile Network Code (MNC).";

      min-elements 1;
      max-elements 6;
      key "mcc mnc";
      uses types3gpp:PLMNId;
    }

    leaf sBIFQDN {
      description "The FQDN of the registered NF instance in the service-based
        interface.";
      type inet:domain-name;
    }

    list sNSSAIList {
      description "List of S-NSSAIs the managed object is capable of supporting.
                   (Single Network Slice Selection Assistance Information)
                   An S-NSSAI has an SST (Slice/Service type) and an optional SD
                   (Slice Differentiator) field.";
      //optional support
      reference "3GPP TS 23.003";
      key "sd sst";
      uses types5g3gpp:SNssai;
    }

    list managedNFProfile {
      key idx;
      leaf idx { type uint32; }
      min-elements 1;
      max-elements 1;
      description "Profile definition of a Managed NF (See TS 23.501)";
      uses mnfp3gpp:ManagedNFProfileGrp;
    }
  }

  typedef DataSetId {
    type enumeration {
      enum SUBSCRIPTION;
      enum POLICY;
      enum EXPOSURE;
      enum APPLICATION;
    }
  }

  augment "/me3gpp:ManagedElement" {
    list UDRFunction {
      description "5G Core UDR Function";
      reference "3GPP TS 28.541";
      key id;
      uses top3gpp:Top_Grp;
      container attributes {
        uses UDRFuntionGrp;
      }
      uses mf3gpp:ManagedFunctionContainedClasses;
    }
  }
}
