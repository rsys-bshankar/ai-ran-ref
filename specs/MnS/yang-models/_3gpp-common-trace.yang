module _3gpp-common-trace {
  yang-version 1.1;
  namespace "urn:3gpp:sa5:_3gpp-common-trace";
  prefix "trace3gpp";

  import _3gpp-common-top { prefix top3gpp; }
  import _3gpp-common-yang-extensions {prefix yext3gpp; }
  import ietf-inet-types { prefix inet; }
  import _3gpp-common-files { prefix files3gpp; }
  import _3gpp-common-yang-types { prefix types3gpp; }
  import _3gpp-5g-common-yang-types {prefix types5g3gpp; }

  organization "3GPP SA5";
  contact "https://www.3gpp.org/DynaReport/TSG-WG--S5--officials.htm?Itemid=464";

  description "Trace handling
    Copyright 2026, 3GPP Organizational Partners (ARIB, ATIS, CCSA, ETSI, TSDSI,
    TTA, TTC). All rights reserved.";
  reference "3GPP TS 28.623
      Generic Network Resource Model (NRM)
      Integration Reference Point (IRP);
      Solution Set (SS) definitions
      3GPP TS 28.622
      Generic Network Resource Model (NRM)
      Integration Reference Point (IRP);
      Information Service (IS)" ;

  revision 2026-08-01 { reference CR-0627; }
  revision 2026-04-01 { reference "CR-0623" ; }
  revision 2026-03-19 { reference "CR-0618" ; }
  revision 2026-02-07 { reference "CR-1682" ; }
  revision 2025-10-07 { reference "CR-0573" ; }    
  revision 2025-10-01 { reference "CR-0578" ; }
  revision 2025-08-07 { reference "CR-0551 CR-0552 CR-0562" ; }
  revision 2025-05-07 { reference "CR-0532 CR-0536 CR-0540" ; }
  revision 2025-02-07 { reference "CR-0504" ; }
  revision 2025-02-05 { reference "CR-0461" ; }
  revision 2024-11-25 { reference "CR-0492" ; }
  revision 2024-11-07 { reference "CR-0480"; }
  revision 2024-10-01 { reference "CR-0457"; }
  revision 2024-08-13 { reference "CR-0387 CR-0377"; }
  revision 2024-08-07 { reference "CR-0405 CR-0421 CR-0379"; }
  revision 2024-05-12 { reference "CR-0401"; }
  revision 2024-05-06 { reference CR-0359; }
  revision 2024-04-06 { reference "CR-0342"; }
  revision 2024-01-29 { reference "CR-0316"; }
  revision 2023-11-06 { reference "CR-0290 CR-0294"; }
  revision 2023-11-03 { reference CR-0302 ; }
  revision 2023-09-18 { reference CR-0271 ; }
  revision 2023-08-10 { reference CR-0261; }
  revision 2023-04-26 { reference CR-0250; }
  revision 2023-02-18 { reference "CR-0234"; }
  revision 2023-02-16 { reference "CR-0233"; }
  revision 2022-09-30 { reference CR-0191 ; }
  revision 2022-04-27 { reference "CR-0159"; }
  revision 2021-10-18 { reference "CR-0139"; }
  revision 2021-07-22 { reference "CR-0137"; }
  revision 2021-01-25 { reference "CR-0122"; }
  revision 2020-11-16 { reference "CR-0117"; }
  revision 2020-08-06 { reference "CR-0102"; }

  feature FilesUnderTraceJob {
    description "Files shall be contained under TraceJob";
  }

  grouping FreqInfoGrp {
    description "Represents the FreqInfo dataType.
      This <<dataType>> defines the RF reference frequency and the frequency
      operating bands used in a cell for a given direction (UL or DL) in FDD
      or for both UL and DL directions in TDD";

    leaf arfcn {
      type uint32 {
        range 0..3279165;
      }
      mandatory true;
      description "RF Reference Frequency as defined in TS 38.104,
        clause 5.4.2.1. The frequency provided identifies the absolute
        frequency position of the reference resource block (Common RB 0)
        of the carrier. Its lowest subcarrier is also known as Point A.";
    }

    leaf-list freqBands {
      type uint32 {
        range 1..1024;
      }
      min-elements 1;
      description "List of NR frequency operating bands. Primary NR
        Operating Band as defined in TS 38.104, clause 5.4.2.3.
        The value 1 corresponds to n1, value 2 corresponds to NR operating
        band n2, etc.";
    }
  }

  grouping AreaConfigGrp {
    description "Represents the AreaConfig dataType.
      This <<dataType>> defines the area for which measurement logging should
      be performed. It is described by a list of cells and a list of
      frequencies.";

    list freqInfo {
      key arfcn;
      min-elements 1;
      max-elements 32;
      description "It specifies the carrier frequency and bands used in
        a cell.";

      uses FreqInfoGrp ;
    }

    leaf-list pciList {
      type uint32 {
        range 0..1007;
      }
      min-elements 1;
      max-elements 32;
      description "List of neighbour cells subject for MDT scope.";
    }
  }

  grouping ExcessPacketDelayThresholdsGrp {
    description "Represents the ExcessPacketDelayThresholds dataType.
      This <<dataType>> defines a excess packet delay threshold information
      to enable the calculation of the PDCP Excess Packet Delay in the
      uplink in case of M6 uplink measurements are requested. The excess
      packet delay threshold information is specified with the 5QI value
      and excess packet delay threshold value.";

    leaf fiveQIValue {
      type uint8;
      mandatory true;
      description "It indicates 5QI value.";
    }

    leaf excessPacketDelayThresholdValue {
      type decimal64 {
        fraction-digits 2;
        range 0.25|0.5|1|2|4|5|10|20|30|40|50|60|70|80|90|100|150|300|500 ;
      }
      mandatory true;
      units milliseconds;
      description "Value of excess packet delay threshold
        for M6 UL measurement in milliseconds.";
    }
  }

  grouping TraceReferenceGrp {
    description "Represents the TraceReference dataType.
      This <<dataType>> defines a globally unique identifier, which uniquely
      identifies the Trace Session that is created by the TraceJob. It is
      composed of the MCC, MNC (resulting in PLMN identifier) and the
      trace identifier.";

      uses types3gpp:PLMNId;  // mcc+mnc

      leaf traceId {
        type string {
          pattern "[0-9a-fA-F]{6}";
        }
        mandatory true;
        description "An identifier, which identifies the Trace
          (together with MCC and MNC). This is a 3 byte Octet String,
          expressed in hexadecimal form e.g., '1a7b3d').";
      }
  }

  grouping MbsfnAreaGrp {
    description "Represents the MbsfnArea dataType.
      This <<dataType>> defines a MBSFN area. It is composed of the MBSFN Area
      identifier and the carrier frequency (EARFCN).";

    leaf mbsfnAreaId {
      type uint32 {
        range 1..max;
      }
      mandatory true;
      description "MBSFN Area Identifier";
    }

    leaf earfcn{
      type uint32 {
        range 1..max;
      }
      mandatory true;
      description "Carrier Frequency";
    }
  }

  grouping TraceConfigGrp {

    description "Defines the configuration parameters of TraceJob
      which are specific for Trace or combined Trace and Immediate MDT.
      The attribute listOfNeTypes specifies the network elements to be
      traced. The optional attribute listOfInterfaces allows to specify
      the individual interfaces of the network elements to be recorded.
      The attribute traceDepth allows to configure the level of detail
      of the information which shall be recorded.  For trace the reporting
      is event based, where the triggering event is configured with
      attribute triggeringEvents. For each triggering event the first and
      last message (start/stop triggering event) to record  are specified.";

      typedef MSCServerInterfaces {
        type enumeration {
          enum A ;
          enum Iu-CS ;
          enum Mc ;
          enum MAP-G ;
          enum MAP-B ;
          enum MAP-E ;
          enum MAP-F ;
          enum MAP-D ;
          enum MAP-C ;
          enum CAP ;
        }
      }
      typedef MGWInterfaces {
        type enumeration {
          enum Mc ;
          enum Nb-UP ;
          enum Iu-UP ;
        }
      }
      typedef RNCInterfaces {
        type enumeration {
          enum Iu-CS ;
          enum Iu-PS ;
          enum Iur ;
          enum Iub ;
          enum Uu ;
        }
      }
      typedef SGSNInterfaces {
        type enumeration {
          enum Gb ;
          enum Iu-PS ;
          enum Gn ;
          enum MAP-Gr ;
          enum MAP-Gd ;
          enum MAP-Gf ;
          enum Ge ;
          enum Gs ;
          enum S6d ;
          enum S4 ;
          enum S3 ;
          enum S13 ;
        }
      }
      typedef GGSNInterfaces {
        type enumeration {
          enum Gn ;
          enum Gi ;
          enum Gmb ;
        }
      }
      typedef S-CSCFInterfaces {
        type enumeration {
          enum Mw ;
          enum Mg ;
          enum Mr ;
          enum Mi ;
        }
      }
      typedef P-CSCFInterfaces {
        type enumeration {
          enum Gm ;
          enum Mw ;
        }
      }
      typedef I-CSCFInterfaces {
        type enumeration {
          enum Cx ;
          enum Dx ;
          enum Mg ;
          enum Mw ;
        }
      }
      typedef MRFCInterfaces {
        type enumeration {
          enum Mp ;
          enum Mr ;
        }
      }
      typedef MGCFInterfaces {
        type enumeration {
          enum Mg ;
          enum Mj ;
          enum Mn ;
        }
      }
      typedef IBCFInterfaces {
        type enumeration {
          enum Ix ;
          enum Mx ;
        }
      }
      typedef E-CSCFInterfaces {
        type enumeration {
          enum Mw ;
          enum Ml ;
          enum Mm ;
          enum Mi-Mg ;
        }
      }
      typedef BGCFInterfaces {
        type enumeration {
          enum Mi ;
          enum Mj ;
          enum Mk ;
        }
      }
      typedef ASInterfaces {
        type enumeration {
          enum Dh ;
          enum Sh ;
          enum ISC ;
          enum Ut ;
        }
      }
      typedef HSSInterfaces {
        type enumeration {
          enum MAP-C ;
          enum MAP-D ;
          enum Gc ;
          enum Gr ;
          enum Cx ;
          enum S6d ;
          enum S6a ;
          enum Sh ;
        }
      }
      typedef EIRInterfaces {
        type enumeration {
          enum MAP-F ;
          enum S13 ;
          enum MAP-Gf ;
        }
      }
      typedef BM-SCInterfaces {
        type enumeration {
          enum Gmb ;
        }
      }
      typedef MMEInterfaces {
        type enumeration {
          enum S1-MME ;
          enum S3 ;
          enum S6a ;
          enum S10 ;
          enum S11 ;
          enum S13 ;
        }
      }
      typedef SGWInterfaces {
        type enumeration {
          enum S4 ;
          enum S5 ;
          enum S8 ;
          enum S11 ;
          enum Gxc ;
        }
      }
      typedef PDN_GWInterfaces {
        type enumeration {
          enum S2a ;
          enum S2b ;
          enum S2c ;
          enum S5 ;
          enum S6b ;
          enum Gx ;
          enum S8 ;
          enum SGi ;
        }
      }
      typedef eNBInterfaces {
        type enumeration {
          enum S1-MME ;
          enum X2 ;
        }
      }
      typedef en-gNBInterfaces {
        type enumeration {
          enum S1-MME ;
          enum X2 ;
          enum Uu ;
          enum F1-C ;
          enum E1 ;
        }
      }
      typedef AMFInterfaces {
        type enumeration {
          enum N1 ;
          enum N2 ;
          enum N8 ;
          enum N11 ;
          enum N12 ;
          enum N14 ;
          enum N15 ;
          enum N20 ;
          enum N22 ;
          enum N26 ;
        }
      }
      typedef AUSFInterfaces {
        type enumeration {
          enum N12 ;
          enum N13 ;
        }
      }
      typedef NEFInterfaces {
        type enumeration {
          enum N29 ;
          enum N30 ;
          enum N33 ;
        }
      }
      typedef NRFInterfaces {
        type enumeration {
          enum N27 ;
        }
      }
      typedef NSSFInterfaces {
        type enumeration {
          enum N22 ;
          enum N31 ;
        }
      }
      typedef PCFInterfaces {
        type enumeration {
          enum N5 ;
          enum N7 ;
          enum N15 ;
        }
      }
      typedef SMFInterfaces {
        type enumeration {
          enum N4 ;
          enum N7 ;
          enum N10 ;
          enum N11 ;
          enum S5-C ;
          enum N38 ;
          enum N16 ;
          enum N16a ;
        }
      }
      typedef SMSFInterfaces {
        type enumeration {
          enum N20 ;
          enum N21 ;
        }
      }
      typedef UDMInterfaces {
        type enumeration {
          enum N8 ;
          enum N10 ;
          enum N13 ;
          enum N21 ;
        }
      }
      typedef UPFInterfaces {
        type enumeration {
          enum N4 ;
        }
      }
      typedef ng-eNBInterfaces {
        type enumeration {
          enum NG-C ;
          enum Xn-C ;
          enum Uu ;
        }
      }
      typedef gNB-CU-CPInterfaces {
        type enumeration {
          enum NG-C ;
          enum Xn-C ;
          enum Uu ;
          enum F1-C ;
          enum E1 ;
          enum X2-C ;
        }
      }
      typedef gNB-CU-UPInterfaces {
        type enumeration {
          enum E1 ;
        }
      }
      typedef gNB-DUInterfaces {
        type enumeration {
          enum F1-C ;
      }
    }



  leaf-list listOfInterfaces {
      type union {
        type MSCServerInterfaces;
        type MGWInterfaces;
        type RNCInterfaces;
        type SGSNInterfaces;
        type GGSNInterfaces;
        type S-CSCFInterfaces;
        type P-CSCFInterfaces;
        type I-CSCFInterfaces;
        type MRFCInterfaces;
        type MGCFInterfaces;
        type IBCFInterfaces;
        type E-CSCFInterfaces;
        type BGCFInterfaces;
        type ASInterfaces;
        type HSSInterfaces;
        type EIRInterfaces;
        type BM-SCInterfaces;
        type MMEInterfaces;
        type SGWInterfaces;
        type PDN_GWInterfaces;
        type eNBInterfaces;
        type en-gNBInterfaces;
        type AMFInterfaces;
        type AUSFInterfaces;
        type NEFInterfaces;
        type NRFInterfaces;
        type NSSFInterfaces;
        type PCFInterfaces;
        type SMFInterfaces;
        type SMSFInterfaces;
        type UDMInterfaces;
        type UPFInterfaces;
        type ng-eNBInterfaces;
        type gNB-CU-CPInterfaces;
        type gNB-CU-UPInterfaces;
        type gNB-DUInterfaces;
      }
      description "Specifies the interfaces that need to be traced in the given
        ManagedEntityFunction.The attribute is applicable only for Trace. In
        case this attribute is not used, it carries a null semantic.";
      reference "Clause 5.5 of 3GPP TS 32.422 for additional details on the
        allowed values.";

    }

    leaf-list listOfNeTypes {
      type enumeration {
        enum MSC_SERVER;
        enum SGSN;
        enum MGW;
        enum GGSN;
        enum RNC;
        enum BM_SC;
        enum MME;
        enum SGW;
        enum PGW;
        enum ENB;
        enum EN_GNB;
        enum GNB_CU_CP;
        enum GNB_CU_UP;
        enum GNB_DU;
      }
      description "Specifies the network element types where the trace should
        be activated. The attribute is applicable only for Trace with
        Signalling Based Trace activation.";
      reference "Clause 5.4 of 3GPP TS 32.422. ";
    }

    leaf traceDepth {
      when 'contains(../../jobType, "TRACE")';
      type enumeration  {
        enum MINIMUM;
        enum MEDIUM;
        enum MAXIMUM;
        enum VENDORMINIMUM;
        enum VENDORMEDIUM;
        enum VENDORMAXIMUM;
      }
      default MAXIMUM;
      description "It specifies the trace depth. The attribute is applicable
      only for Trace.";
      reference "Clause 5.3 of 3GPP TS 32.422.";
    }

    list triggeringEvents {
      key idx;
      description "It specifies the triggering event parameter of the trace
        session. The attribute is applicable only for Trace.";
      reference "Clause 5.1 of 3GPP TS 32.422";
      leaf idx { type uint32; }
      max-elements 1;

      leaf-list MSC_SERVER {
        type enumeration {
          enum MO_MT_CALLS;
          enum MO_MT_SMS;
          enum LU_IMSIattach_IMSIdetach;
          enum SS;
        }
      }

      leaf-list SGSN {
        type enumeration {
          enum PDPcontext;
          enum MO_MT_SMS;
          enum RAU_GPRSattach_GPRSdetach;
          enum MBMScontext;
        }
      }


      leaf-list MGW {
        type enumeration {
          enum CONTEXT;
        }
      }

      leaf-list GGSN {
        type enumeration {
          enum PDPcontext;
          enum MBMScontext;
        }
      }

      leaf-list IMS {
        type enumeration {
          enum SIPsession_StandaloenTransaction;
        }
      }

      leaf-list BM_SC {
        type enumeration {
          enum MBMSactivation;
        }
      }

      leaf-list MME {
        type enumeration {
          enum UEinitiatedPDNconnectivityRequest;
          enum ServiceRequest;
          enum InitialAttach_TAU_Detach;
          enum UEInitiatedPDNdisconnection;
          enum BearerActivationModificationDeletion;
          enum Handover;
        }
      }


      leaf-list SGW {
        type enumeration {
          enum PDNconnectionCreation;
          enum PDNconnectionTermination;
          enum BearerActivationModificationDeletion;
        }
      }

      leaf-list PGW {
        type enumeration {
          enum PDNconnectionCreation;
          enum PDNconnectionTermination;
          enum BearerActivationModificationDeletion;
        }
      }

      leaf-list AMF {
        type enumeration {
          enum Registration;
          enum ServiceRequest;
          enum Handover;
          enum UEderegistration;
          enum NetworkDeregistration;
          enum UEMobilityFromEPC;
          enum UEMobilityToEPC;
          enum CovergedChargingService;
        }
      }

      leaf-list SMF {
        type enumeration {
          enum PDUsessionEstablishment;
          enum PDUsessionModification;
          enum PDUsessionRelease;
          enum PDUsessionUPactivationDeactivation;
          enum MobilityBtw3gppAndN3gppTo5GC;
          enum MobilityFromEpc;
          enum MobilityBtwISMForVSMF;
          enum CovergedChargingService;
          enum OfflineOnlyCharging;
        }
      }

      leaf-list PCF {
        type enumeration {
          enum AMpolicy;
          enum SMpolicy;
          enum Authorization;
          enum BDTpolicy;
          enum SpendingLimitControl;
        }
      }

      leaf-list UPF {
        type enumeration {
          enum N4Session;
        }
      }

      leaf-list AUSF {
        type enumeration {
          enum UEauthentication;
        }
      }

      leaf-list NEF {
        type enumeration {
          enum EventExposure;
          enum PFDmanagement;
          enum ParameterProvisiong;
          enum Trigger;
        }
      }

      leaf-list NRF {
        type enumeration {
          enum NFmanagement;
          enum NFdiscovery;
        }
      }

      leaf-list NSSF {
        type enumeration {
          enum NSSelection;
          enum NSSAI;
        }
      }

      leaf-list SMSF {
        type enumeration {
          enum SMService;
        }
      }

      leaf-list UDM {
        type enumeration {
          enum UEcontext;
          enum SubscriberData;
          enum UEauthentication;
          enum EventExposure;
        }
      }
    }
  }

  grouping EventTriggerConfigGrp {
    description "Represent the EventTriggerConfig data type. Defines the 
      configuration parameters of trigger event used for M10 measurement in NR. 
      For details, please refer to TS 32.422 subclause 5.10.45.";
    
    leaf eventType {
      type enumeration {
        enum eventA1 { value 0; }
        enum eventA2 { value 1; }
      }
      mandatory true;
      description "It indicates the event type. Either Event A1 or Event A2 
        can be configured. See also clause 5.10.45 of TS 32.422.";
    }
    
    leaf thresholdRAN {
      type uint8 {
        range 0..127;
      }
      mandatory true;
      description "Threshold parameter for an event. It is used to define the 
        entering and leaving condition of the event. For further details see 
        RSRP-Range in TS 38.331. See also clause 5.10.45 of TS 32.422";
    }
    
    leaf measurementQuantityRAN {
      type int32;
      mandatory true;
      description "It indicates the measurement quantity. For further details 
        see MeasTriggerQuantity in TS 38.331. See also clause 5.10.45 of 
        TS 32.422";
    }
    
    leaf hysteresisRAN {
      type uint8 {
        range 0..30;
      }
      mandatory true;
      description "Hysteresis parameter for an event. It is used to define the 
        entering and leaving condition of the event. For further details see 
        Hysteresis in TS 38.331. See also clause 5.10.45 of TS 32.422";
    }
    
    leaf timeToTriggerRAN {
      type enumeration {
        enum 0ms { value 0; }
        enum 40ms { value 1; }
        enum 64ms { value 2; }
        enum 80ms { value 3; }
        enum 100ms { value 4; }
        enum 128ms { value 5; }
        enum 160ms { value 6; }
        enum 256ms { value 7; }
        enum 320ms { value 8; }
        enum 480ms { value 9; }
        enum 512ms { value 10; }
        enum 640ms { value 11; }
        enum 1024ms { value 12; }
        enum 1280ms { value 13; }
        enum 2560ms { value 14; }
        enum 5120ms { value 15; }
      }
      mandatory true;
      description "It defines the time during which specific criteria for the 
        event needs to be met in order to trigger an action. 
        For further details see TimeToTrigger in TS 38.331 and clause 5.10.45 
        of TS 32.422.";
    }
  }
  
  grouping ImmediateMdtConfigGrp {
   description "Represents the ImmediateMdtConfig dataType.
      This <<dataType>> defines the configuration parameters of
      IOC TraceJob which are specific for Immediate MDT or combine
      Trace and Immediate MDT.

      The optional attribute positioningMethod allows to specify
      the positioning methods to use.

      The following attributes are conditional available based on the
      measurements configured in listOfMeasurements:
        -reportInterval (conditional for M1 in LTE or NR and M1/M2 in UMTS),
        -reportAmount (conditional for M1/M2 in UMTS),
        -reportAmountM1LTE (conditional for M1 in LTE),
        -reportAmountM4LTE (conditional for M4 in LTE),
        -reportAmountM5LTE (conditional for M5 in LTE),
        -reportAmountM6LTE (conditional for M6 in LTE),
        -reportAmountM7LTE (conditional for M7 in LTE),
        -reportAmountM1NR (conditional for M1 in NR),
        -reportAmountM4NR (conditional for M4 in NR),
        -reportAmountM5NR (conditional for M5 in NR),
        -reportAmountM6NR (conditional for M6 in NR),
        -reportAmountM7NR (conditional for M7 in NR),
        -reportingTrigger (conditional for M1 in LTE or NR and M1/M2 in UMTS),
        -eventThreshold (conditional for A2 event reporting or A2 event
          triggered periodic reporting),
        -collectionPeriodRRMNR (conditional for M4 and M5 in NR),
        -collectionPeriodM6NR (conditional for M6 in NR),
        -collectionPeriodM7NR (conditional for M7 in NR),
        -collectionPeriodRRMLTE (conditional for M3 in LTE),
        -measurementPeriodLTE (conditional for M4 and M5 in LTE),
        -collectionPeriodM6LTE (conditional for M6 in LTE),
        -collectionPeriodM7LTE (conditional for M7 in LTE),
        -collectionPeriodRRMUMTS (conditional for M4 and M5 in UMTS),
        -measurementPeriodUMTS (conditional for M6 and M7 in UMTS),
        -measurementQuantity (conditional for 1F event reporting),
        -beamLevelMeasurement (conditional for M1 in NR),
        -excessPacketDelayThresholds (conditional for M6 UL measurement in NR).
        -layerOneRsrpPeriodicity (conditional for M10 measurements in NR),
        -eventTriggerConfig (conditional for event reporting for M10 measuremen

       For immediate MDT, the measurement reporting is dependent on the
       configured measurements:

        - For measurement M1 in LTE or NR, it is possible to select between
        periodical, event triggered, event triggered periodic reporting or
        reporting according to all configured RRM event triggers. For M1 and M2
        measurement in UMTS, it is possible to select between periodical, event
        triggered reporting or reporting according to all configured RRM event
        triggers. Parameter reportingTrigger determines which of the reporting
        methods is selected and in case of event triggered or event-triggered
        periodic, which is the decisive event type. For periodical reporting,
        parameters reportInterval and reportAmount determine the interval between
        two successive reports and the number of reports. This means the
        periodical reporting terminates after reportAmount reports have been
        sent as long as reportAmount is configured with a value different from
        infinity. For event-triggered periodic reporting, these two parameters
        apply in addition to parameter eventThreshold which determines the
        threshold of the event. In this case up to reportAmount reports are
        sent with a periodicity of reportInterval after the entering condition
        is fulfilled. The reporting is stopped, if the leaving condition is
        fulfulled and is restarted if the configured event reoccurs. For event
        based reporting, there is only one report sent after the event occurs.
        The parameters to configure are reportingTrigger and eventThreshold.
        In case of UMTS and 1f event reporting, additionally parameter
        measurementQuantity is necessary in order to determine for which
        measurement(s) the event threshold is applicable.  Parameter
        beamLevelMeasurement determines whether beam level measurements shall
        be included in case of NR.

        - For measurement M2 in LTE or NR, reporting is according to RRM
        configuration, see TS 38.321, TS 36.321 and TS 38.331, TS 36.331.

        - For measurement M4 in UMTS, reporting is either according to RRM
        configuration, see TS 25.321 and TS 25.331 or periodic or event
        triggered periodic using parameter collectionPeriodRRMUMTS and
        eventThresholdUphUMTS.

        - For measurement M3 in UMTS, the reporting is done upon
        availability, see TS 37.320.

        - For measurements M4, M5, M6 and M7 in NR, for measurements
        M3, M4, M5, M6 and M7 in LTE and for measurements M5, M6 and M7
        in UMTS periodical reporting is applied. The configurable parameter
        is the interval between two measurements (collectionPeriodRRMNR,
        collectionPeriodM6NR, collectionPeriodM7NR, collectionPeriodRRMLTE,
        measurementPeriodLte, collectionPeriodM6LTE, collectionPeriodM7LTE,
        collectionPeriodRRMUMTS, measurementPeriodUMTS) and the number of
        reports (reportAmountM4NR, reportAmountM5NR, reportAmountM6NR,
        reportAmountM7NR, reportAmountM4LTE, reportAmountM5LTE,
        reportAmountM6LTE,reportAmountM7LTE).  If no collection period
        is configured for M5 in UMTS, all available measurements are
        logged according to RRM configuration.

        - Measurements M8 and M9 in NR or LTE are reported according to
        configured M1 and/or M6 related UE measurement reporting.
        
        - For management based Immediate MDT M10 measurements 
        layerOneRsrpPeriodicity in NR, the 
        measurement is optionally triggered with periodically or event based . 
        The parameter layerOneRsrpPeriodicity determines the interval between 
        two successive UE measurements. If parameter eventTriggerConfig is 
        configured, the logging is performed only at the condition indicated 
        by eventTriggerConfigis met.
        ";

    leaf listOfMeasurements {
      when 'contains(../../../jobType, "IMMEDIATE_MDT")';
      type uint32;
      description "It specifies the UE measurements that shall be
        collected in an Immediate MDT job. The attribute is
        applicable only for Immediate MDT.";
      reference "Clause 5.10.3 of 3GPP TS 32.422.";
    }

   leaf reportingTrigger {
      when 'contains(../../../jobType, "IMMEDIATE_MDT")';
      type uint8;
      description "It specifies whether periodic or event based measurements
        should be collected.
        The attribute is applicable only for Immediate MDT and when the
        listOfMeasurements is configured for M1 (for both UMTS and LTE)
        or M2 (only for UMTS).";
      reference "Clause 5.10.4 of 3GPP TS 32.422.";
    }

   leaf reportInterval {
      when 'contains(../../../jobType, "IMMEDIATE_MDT") and '
        + '(../reportingTrigger mod 2 = 1)';
      type uint32 {
        range "120|240|250|480|500|640|1000|1024|2000|2048|3000|4000|"
          +"5120|6000|8000|10240|12000|16000|20000|"
          +"20480|24000|28000|32000|40960|60000|64000|"
          +"360000|720000|1800000|3600000";
      }
      units milliseconds;
      description "It specifies the interval between the periodical measurements
        that shall be taken when the UE is in connected mode.
        The attribute is applicable only for Immediate MDT and when
        reportingTrigger is configured for periodical measurements.";
      reference "5.10.5 of 3GPP TS 32.422.";
    }

   leaf reportAmount {
      when 'contains(../../../jobType, "IMMEDIATE_MDT") and '
        + '(../reportingTrigger mod 2 = 1)';
      type union {
        type uint32 {
          range "1|4|8|16|32|64" ;
        }
        type enumeration {
          enum INFINITY;
        }
      }
      description "It specifies the number of measurement reports that shall be
        taken for periodic reporting while the UE is in connected.
        The attribute is applicable only for Immediate MDT and when
        reportingTrigger is configured for periodical measurements.";
      reference "Clause 5.10.6 of 3GPP TS 32.422";
    }

   leaf eventThreshold {
      when 'contains(../../../jobType, "IMMEDIATE_MDT")';
      type int64;
      description "Specifies the threshold which should trigger the reporting
        in case A2 event reporting in LTE or 1F/1l event in UMTS. The attribute
        is applicable only for Immediate MDT and when reportingTrigger is
        configured for A2 event in LTE or 1F event or 1l event in UMTS.";
      reference "Clauses 5.10.7 and 5.10.7a of 3GPP TS 32.422";
    }

   leaf collectionPeriodRRMNR {
      when 'contains(../../../jobType, "IMMEDIATE_MDT")';
      type uint32 {
        range "1024|2048|5120|10240|60000";
      }
      units milliseconds;
      description "Specifies the collection period for collecting RRM
        configured measurement samples for M4, M5 in NR. The attribute is
        applicable only for Immediate MDT.";
      reference "Clause 5.10.30 of 3GPP TS 32.422";
    }

   leaf collectionPeriodM6NR {
      when 'contains(../../../jobType, "IMMEDIATE_MDT")';
      type enumeration {
        enum 120ms;
        enum 240ms;
        enum 480ms;
        enum 640ms;
        enum 1024ms;
        enum 2048ms;
        enum 5120ms;
        enum 10240ms;
        enum 20480ms;
        enum 40960ms;
        enum 1min;
        enum 6min;
        enum 12min;
        enum 30min;
      }
      description "It specifies the collection period for the Packet Delay
        measurement (M6) for NR MDT taken by the gNB. The attribute is
        applicable only for Immediate MDT. ";
      reference "clause 5.10.34 of  TS 32.422";
    }

    leaf collectionPeriodM7NR {
      when 'contains(../../../jobType, "IMMEDIATE_MDT")';
      type uint32 {
        range "1..60";
      }
      description "It specifies the collection period for the Packet Loss Rate
        measurement (M7) for NR MDT taken by the gNB. The attribute is
        applicable only for Immediate MDT.";
      reference "clause 5.10.35 of  TS 32.422";
    }

   leaf collectionPeriodRRMLTE {
      when 'contains(../../../jobType, "IMMEDIATE_MDT")';
       type enumeration {
        enum 100ms;
        enum 1000ms;
        enum 1024ms;
        enum 1280ms;
        enum 2048ms;
        enum 2560ms;
        enum 5120ms;
        enum 10000ms;
        enum 10240ms;
        enum 1min;
      }
      description "Specifies the collection period for collecting RRM configured
        measurement samples for M3 in LTE. The attribute is applicable only
        for Immediate MDT.";
      reference "Clause 5.10.20 of 3GPP TS 32.422.";
    }

   leaf measurementPeriodLTE {
      when 'contains(../../../jobType, "IMMEDIATE_MDT")';
      type enumeration {
        enum 1024ms;
        enum 2048ms;
        enum 5120ms;
        enum 10240ms;
        enum 1min;
      }
      mandatory true;
      description "It specifies the measurement period for the
        Data Volume (M4) and Scheduled IP throughput
        measurements (M5) for LTE MDT taken by the eNB.
        The attribute is applicable only for Immediate MDT.";
      reference "Clause 5.10.23 of 3GPP TS 32.422.";
    }

    leaf collectionPeriodM6LTE {
      when 'contains(../../../jobType, "IMMEDIATE_MDT")';
      type uint32 {
        range "1024|2048|5120|10240";
      }
      units milliseconds;
      description "Specifies the collection period for the Packet Delay
        measurement (M6) for MDT taken by the eNB. The attribute is applicable
        only for Immediate MDT. In case this attribute is not used,
        it carries a null semantic.";
      reference "Clause 5.10.32 of  TS 32.422. ";
    }

    leaf collectionPeriodM7LTE {
      when 'contains(../../../jobType, "IMMEDIATE_MDT")';
      type uint16 {
        range 1..60 ;
      }
      description "It specifies the collection period for the Packet Loss Rate
        measurement (M7) for LTE MDT taken by the eNB. The attribute is
        applicable only for Immediate MDT.";
      reference "Clause 5.10.33 of  TS 32.422.";
    }

    leaf eventThresholdUphUMTS {
      when 'contains(../../../jobType, "IMMEDIATE_MDT")';
      type uint16 {
        range 0..31 ;
      }
      description "It specifies the threshold which should trigger
        the reporting in case of event-triggered periodic reporting for M4
        (UE power headroom measurement) in UMTS.";
        reference "Clause 5.10.39 of TS 32.422.";
    }

    leaf collectionPeriodRRMUMTS {
      when 'contains(../../../jobType, "IMMEDIATE_MDT")';
      type uint32 {
        range "100|250|500|1000|2000|"
          +"3000|4000|6000";
      }
      units milliseconds;
      description "Specifies the collection period for collecting RRM configured
        measurement samples for M3, M4, M5 in UMTS. The attribute is applicable
        only for Immediate MDT. ";
      reference "Clause 5.10.21 of 3GPP TS 32.422.";
    }

    leaf measurementPeriodUMTS {
      when 'contains(../../../jobType, "IMMEDIATE_MDT")';
      type uint32 {
        range "1000|2000|3000|4000|6000|8000|12000|16000|20000|"
          +"24000|28000|32000|64000";
      }
      units milliseconds;
      description "It specifies the measurement period for the Data Volume and
        Throughput measurements for MDT taken by RNC.
        The attribute is applicable only for Immediate MDT. In case this
        attribute is not used, it carries a null semantic.";
      reference "Clause 5.10.22 of 3GPP TS 32.422";
    }

    leaf measurementQuantity {
      when 'contains(../../../jobType, "IMMEDIATE_MDT")';
      type enumeration {
        enum CPICH_ECNO;
        enum CPICH_RSCP;
        enum PATHLOSS;
      }
      description "It specifies the measurements that are collected in an MDT
        job for a UMTS MDT configured for event triggered reporting.";
      reference "Clause 5.10.15 of 3GPP TS 32.422.";
    }

    leaf beamLevelMeasurement {
      when 'contains(../../../jobType, "IMMEDIATE_MDT")';
      type boolean;
      default false;
      description "Indicates whether the NR M1 beam level measurements shall
        be included or not.";
      reference "Clause 5.10.40 of 3GPP TS 32.422.";
    }

    leaf positioningMethod {
      when 'contains(../../../jobType, "IMMEDIATE_MDT")';
      type enumeration {
        enum GNSS;
        enum E_CELL_ID;
      }
      description "It specifies what positioning method should be used in the
        MDT job.";
      reference "Clause 5.10.19 of 3GPP TS 32.422.";
    }

    list excessPacketDelayThresholds {
      description "Excess packet delay thresholds info for M6 UL measurement.";
      min-elements 1;
      key idx;
      leaf idx { type string; }
      uses ExcessPacketDelayThresholdsGrp;
    }

    leaf reportAmountM1LTE {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for LTE.";
      reference "Clause 5.10.19 of 3GPP TS 32.422.";
    }

    leaf reportAmountM4LTE {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for LTE.";
      reference "Clause 5.10.6 of TS 32.422.";
    }

    leaf reportAmountM5LTE {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for LTE.";
      reference "Clause 5.10.6 of TS 32.422.";
    }

    leaf reportAmountM6LTE {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for LTE.";
      reference "Clause 5.10.6 of TS 32.422.";
    }

    leaf reportAmountM7LTE {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for LTE.";
      reference "Clause 5.10.6 of TS 32.422.";
    }

    leaf reportAmountM1NR {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for NR.";
      reference "Clause 5.10.6 of TS 32.422.";
    }

    leaf reportAmountM4NR {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for NR.";
      reference "Clause 5.10.6 of TS 32.422.";
    }

    leaf reportAmountM5NR {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for NR.";
      reference "Clause 5.10.6 of TS 32.422.";
    }

    leaf reportAmountM6NR {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for NR.";
      reference "Clause 5.10.6 of TS 32.422.";
    }

    leaf reportAmountM7NR {
      type enumeration {
        enum 1;
        enum 2;
        enum 4;
        enum 8;
        enum 16;
        enum 32;
        enum 64;
        enum INFINITY;
      }
      description "It specifies the number of measurement reports that shall be
        taken for periodic reporting while the UE is in connected mode.
        The attribute is applicable only for Immediate MDT and combined Trace
        and Immediate MDT and when reportingTrigger is configured for periodical
        measurements and applicable only for NR.";
      reference "Clause 5.10.6 of TS 32.422.";
    }
    
    leaf layerOneRsrpPeriodicity {
      type enumeration {
        enum 2 {value 0; }
        enum 3 {value 1; }
        enum 4 {value 2; }
        enum 5 {value 3; }
      }
      description "It defines the periodicity that the UE shall use for the  
        M10 measurements.";
    }
    
    list eventTriggerConfig {
      description "It specifies the event-triggered configuration used for M10 
        measurements.";
        max-elements 1;
        key idx;
        leaf idx { type uint32; }
      uses EventTriggerConfigGrp;
    }
  }

  grouping LoggedMdtConfigGrp {
    description "This <<dataType>> defines the configuration parameters of
      IOC TraceJob which are specific for Logged MDT or Logged MBSFN MDT.

      Based on the value configured for attribute jobType in IOC TraceJob,
      different attributes are available. In case of LOGGED_MDT_ONLY, the
      attributes reportType, eventListForEventTriggeredMeasurement,
      eventThresholdL1, hysteresisL1, timeToTriggerL1,
      areaConfigurationForNeighCells and npnIdentityList are applicable.
      In case of LOGGED_MBSFN_MDT,
      the attribute mbsfnAreaList is applicable. The optional attribute
      plmnList allows to specify the PLMNs where
      measurement collection, status indication and log reporting is
      allowed, the optional attribute areaConfigurationForNeighCell
      allows to specify the area for which UE is requested to perform
      measurements logging for neighbour cells which have list of
      frequencies.

      For logged MDT in UMTS and LTE, the reporting is periodical. Parameter
      loggingInterval determines the interval between the reports and parameter
      loggingDuration determines how long the configuration is valid meaning
      after this duration has passed no further reports are sent. In NR, the
      reporting can be periodical or event based, determined by parameter
      reportType. For periodical reporting the same parameters as in LTE and
      UMTS apply. For event based reporting,
      parameter eventListForEventTriggeredMeasurement configures the event type,
      namely 'out of coverage' or 'L1 event'. In case 'L1 event' is selected as
      event type, the logging is performed according to parameter loggingInterval
      at regular intervals only when the conditions indicated by
      eventThresholdL1, hysteresisL1, timeToTriggerL1 (defining the thresholds,
      hysteresis and time to trigger) are met and if UE is 'camped normally'
      state (TS 38.331,
      TS 38.304).  In case 'out of coverage' is selected as event type, the
      logging is performed according to parameter loggingInterval at regular
      intervals only when the UE is in 'any cell selection' state.
      Furthermore, logging is performed immediately upon transition from the
      'any cell selection' state to the 'camped normally' state (TS 38.331,
      TS 38.304).";

    leaf traceCollectionEntityId {
      type int64;
      description "It specifies the TCE Id which is sent to the UE in
        Logged MDT.";
      reference "Clause 5.10.11 of 3GPP TS 32.422.";
    }

    leaf loggingDuration {
      when 'contains(../../../jobType, "LOGGED_MDT") or '
         + 'contains(../../../jobType, "LOGGED_MBSFN_MDT")';
      type uint32 {
        range "600|1200|2400|3600|5400|7200";
      }
      units seconds;
      description "Specifies how long the MDT configuration is valid at the
        UE in case of Logged MDT. The attribute is applicable only for
        Logged MDT and Logged MBSFN MDT.";
      reference "Clause 5.10.9 of 3GPP TS 32.422";
    }

    leaf loggingInterval {
      when 'contains(../../../jobType, "LOGGED_MDT") or '
         + 'contains(../../../jobType, "LOGGED_MBSFN_MDT")';
      type enumeration {
        enum 320ms;
        enum 640ms;
        enum 1280ms;
        enum 2560ms;
        enum 5120ms;
        enum 10240ms;
        enum 20480ms;
        enum 30720ms;
        enum 40960ms;
        enum 61440ms;
        enum INFINITY;
      }
      description "Specifies the periodicty for Logged MDT. The attribute is
        applicable only for Logged MDT and Logged MBSFN MDT.";
      reference "Clause 5.10.8 of 3GPP TS 32.422";
    }

    leaf reportType {
      when 'contains(../../../jobType, "IMMEDIATE_MDT")';
      type enumeration {
        enum PERIODICAL;
        enum EVENT_TRIGGERED;
      }
      description "It specifies report type for logged NR MDT";
      reference "Clause 5.10.27 of 3GPP TS 32.422.";
    }

    leaf eventListForEventTriggeredMeasurement {
      when 'contains(../../../jobType, "LOGGED_MDT")';
      type enumeration {
        enum OUT_OF_COVERAGE ;
        enum A2_EVENT ;
      }
      description "Specifies event types for event triggered measurement in the
        case of logged NR MDT.  Each trace session may configure at most one
        event. The UE shall perform logging of measurements only upon certain
        condition being fulfilled:
        - Out of coverage.
        - A2 event.";
      reference "Clause 5.10.28 of 3GPP TS 32.422.";
    }

    leaf eventThresholdL1 {
      when 'contains(../../../jobType, "LOGGED_MDT") or '
         + 'contains(../../../jobType, "LOGGED_MBSFN_MDT")';
      type uint32 {
        range "0..127";
      }
      description "It specifies the threshold which should trigger
        the reporting in case of event based reporting of logged NR MDT.
        The attribute is applicable only for Logged MDT and when reportType
        is configured for event triggered reporting and when
        eventListForEventTriggeredMeasurement is configured for L1 event.";
      reference "clause 5.10.36 of TS 32.422";
    }

    leaf hysteresisL1 {
      when 'contains(../../../jobType, "LOGGED_MDT") or '
         + 'contains(../../../jobType, "LOGGED_MBSFN_MDT")';
      type uint32 {
        range "0..30";
      }
      description "It specifies the hysteresis used within the entry and leave
        condition of the L1 event based reporting of logged NR MDT.
        The attribute is applicable only for Logged MDT, when reportType
        is configured for event triggered reporting and when
        eventListForEventTriggeredMeasurement is configured for L1 event.";
      reference "clause 5.10.37 of TS 32.422";
    }

    leaf timeToTriggerL1 {
      when 'contains(../../../jobType, "LOGGED_MDT") or '
         + 'contains(../../../jobType, "LOGGED_MBSFN_MDT")';
      type int32 {
        range 0|40|64|80|100|128|160|256|320|480|512|640|1024|1280|2560|5120;
      }
      units milliseconds;
      description "It specifies the threshold which should trigger
        the reporting in case of event based reporting of logged NR MDT.
        The attribute is applicable only for Logged MDT, when reportType
        is configured for event triggered reporting and when
        eventListForEventTriggeredMeasurement is configured for L1 event.";
      reference "clause 5.10.38 of TS 32.422";
    }

    list areaConfigurationForNeighCell {
      when 'contains(../../../jobType, "LOGGED_MDT")';
      key "idx";
      leaf idx { type uint32 ; }
      description "It specifies the area for which UE is requested to perform
        measurement logging for neighbour cells which have list of frequencies.
        If it is not configured, the UE shall perform measurement logging for
        all the neighbour cells.

        Applicable only to NR Logged MDT.";
      reference "Clause 5.10.26 of 3GPP TS 32.422.";

      uses AreaConfigGrp;
    }

    list mbsfnAreaList {
      when 'contains(../../../jobType, "LOGGED_MBSFN_MDT")';
      key "mbsfnAreaId earfcn";
      max-elements 8;
      description "The MBSFN Area consists of a MBSFN Area ID and Carrier
        Frequency (EARFCN). The target MBSFN area List can have up to 8 entries.
        This parameter is applicable only if the job type is Logged MBSFN MDT.";
      reference "Clause 5.10.25 of 3GPP TS 32.422.";

      uses MbsfnAreaGrp;
    }

    list nPNIdentityList {
      description "It defines which NPNs that can be served by the NR cell,
        and which CAG IDs or NIDs can be supported by the NR cell for
        corresponding PNI-NPN or SNPN in case of the cell is NPN-only cell.
        (NPN-Identity referring to TS 38.331)";
      key idx;
      max-elements 1;
      uses types3gpp:NpnIdGrp;
      leaf idx { type string;}
    }
  }

  grouping MdtConfigGrp {
    description "Defines the configuration parameters of IOC TraceJob which are
     specific for MDT or any combination of MDT. 
     
     The attribute anonymizationOfMdtData specifies the level of anonymization 
     of MDT data.  
     
     The attribute areaScope defines the area scope
     of MDT, which is specified in clause 5.10.2 of TS 32.422.
     
     The optional attribute sensorInformation allows to specify
     the sensor information to include. 
     
     The attribute trsrPrefixCfg contains the TRSR prefix 
     configuration parameters which shall be used by the NR-RAN nodes 
     during TRSR assignment for a C-MDT job.

     Based on the value configured for attribute jobType in IOC 
     TraceJob, the attributes immediateMdtConfig or loggedMdtConfig 
     or both are available: If the attribute jobType indictes immediate MDT, 
     the attribute immediateMdtConfig is applicable. If the attribute jobType 
     indictes logged MDT or logged MBSFN MDT, the attribute loggedMdtConfig is 
     applicable. If the attribute jobType indictes both immediate MDT and 
     logged MDT, both the attribute immediateMdtConfig and 
     the attribute loggedMdtConfig are applicable.

     The optional attribute plmnList allows to specify the PLMNs where 
     measurements collection, status indication and log reporting is allowed.
     For NTN MDT, if the list of plmnList is included, it will only log 
     measurements for the cells belonging to the listed PLMNs.";

   leaf anonymizationOfMdtData {
      when ../areaScope ;
      type enumeration {
        enum NO_IDENTITY;
        enum TAC_OF_IMEI;
      }
      default NO_IDENTITY;
      description "Specifies level of anonymization of MDT data.
        This attribute is only applicable for management based activation.";
      reference "Clause 5.10.12 of 3GPP TS 32.422";
    }

   list areaScope {
      key "idx";
      leaf idx { type uint32 ; }
      description "It specifies the area where data shall be collected. ";
      max-elements 1;
      uses types5g3gpp:AreaScopeGrp;
    }

   leaf-list sensorInformation {
      type enumeration {
        enum BAROMETRIC_PRESSURE;
        enum UE_SPEED;
        enum UE_ORIENTATION;
      }
      description "It specifies which sensor information shall be included in
        logged NR MDT and immediate NR MDT measurement if they are available.";
      reference "Clause 5.10.29 of 3GPP TS 32.422.";
    }

    list immediateMdtConfig {
      description "The set of parameters specific for Immediate MDT
        configuration.";
      key idx;
      max-elements 1;
      leaf idx { type string; }
      uses ImmediateMdtConfigGrp;
    }

    list loggedMdtConfig {
      description "The set of parameters specific for Logged MDT and Logged
        MBSFN MDT configuration.";
      key idx;
      max-elements 1;
      leaf idx { type string; }
      uses LoggedMdtConfigGrp;
    }

    leaf mNOnly {
      type boolean;
      default false;
      description "Specifies whether the MDT configuration is for MN
        only or not. The value FALSE means the MDT configuration is for
        both MN and SN. The value TRUE means the MDT configuration is
        for MN only.";
    }

    list plmnList {
      key "mcc mnc";
      uses types3gpp:PLMNId;
      max-elements 16;
      description "It indicates the PLMNs where measurement collection, status
        indication and log reporting is allowed.";
      reference "Clause 5.10.24 of 3GPP TS 32.422.";
    }

    list trsrPrefixCfg {
      key "idx";
      max-elements 1;
      description "The TRSR prefix configuration parameters which are used by 
        NR-RAN at TRSR assignment for a given C-MDT job. It defines both the 
        base TRSR prefix and the size of the TRSR prefix. The attribute 
        trstPrefix specifies the base TRSR prefix. The attribute 
        trsrPrefixLength defines the size of base TRSR prefix.";
      reference "Clause 5.10 of 3GPP TS 32.422.";
      leaf idx { type uint32 ; }
      uses trace3gpp:TrsrPrefixCfgGrp ; 
    }   
  }

  grouping UECoreMeasConfigGrp {
    description "Represents the UECoreMeasConfig dataType.
      This <<dataType>> defines the aconfiguration parameters of IOC TraceJob
        which are specific for UE level measurements collection.";

    leaf-list ueCoreMeasurements {
      type string;
      min-elements 1;
      description "List of 5GC UE level measurements identified by name.

        The list may include 5GC UE level measurements defined in TS 28.558,
        or vendor specific measurements.

        For non-3GPP specified 5GC UE level measurements the name is defined
        elsewhere.";
    }

    leaf ueCoreMeasGranularityPeriod {
      type uint32;
      mandatory true;
      units milliseconds;
      description "Granularity period used to produce 5GC UE
        level measurements. The period is defined in milliseconds (ms).";
    }

    leaf nfTypeToMeasure {
      type string;
      mandatory true;
      description "It indicates the type of NE to produce the 5GC UE level
        measurements.

        allowedValues: The NF types represented by the measured object
        classes as defined by f) of the 5GC UE level measurements specified
        in TS 28.558.";
    }

    leaf-list objectInstances {
      type string;
      description "List of object instances.
        Each object instance is identified by its DN.";
    }

    leaf-list rootObjectInstances {
      type string;
      description "List of root object instances.
        Each object instance is identified by its DN and designates
        the root of a substree that contains the root object and all
        descendant objects.";
    }
  }

  grouping TrsrPrefixCfgGrp {
    leaf trsrPrefix {
      type string;
      mandatory true;
      description "A 2 byte Octet String. This is the base TRSR prefix";
    }
    leaf trsrPrefixLength {
      type int32;
      mandatory true;
      description "An integer to indicate how many bits are used for the 
        TRSR prefix";

    }
  }

  grouping TraceJobGrp {

    leaf jobType {
      type enumeration {
        enum IMMEDIATE_MDT_ONLY;
        enum LOGGED_MDT_ONLY;
        enum TRACE_ONLY;
        enum IMMEDIATE_MDT_AND_TRACE;
        enum RLF_REPORT_ONLY;
        enum RCEF_REPORT_ONLY;
        enum LOGGED_MBSFN_MDT;
        enum 5GC_UE_LEVEL_MEASUREMENTS_ONLY;
        enum TRACE_AND_5GC_UE_LEVEL_MEASUREMENTS;
        enum IMMEDIATE_MDT_AND_5GC_UE_LEVEL_MEASUREMENTS;
        enum TRACE_AND_IMMEDIATE_MDT_AND_5GC_UE_LEVEL_MEASUREMENTS;
        enum RRC_REPORT;
        enum IMMEDIATE_MDT_AND_LOGGED_MDT;
      }
      default TRACE_ONLY;
      description "It specifies whether the
        TraceJob represents only MDT, Trace, RLF, RCEF, RRC or 5GC UE
        level measurements job, or a combined job. It also defines the
        MDT mode.";
      reference "Clause 5.9a of 3GPP TS 32.422.";
    }
    leaf-list rrcReportType {
      type enumeration {
        enum RLF_REPORT;
        enum RCEF_REPORT;
        enum SHR;
        enum SPR;
        enum MHI;
        enum RA_REPORT;
      }
    description "Specifies the RRC reports requested. ";
    reference "3GPP TS 38.331";
    }

    list pLMNTarget {
      key "mcc mnc";
      description "It specifies which PLMN that the subscriber of the session to
        be recorded uses as selected PLMN.";
      reference "Clause 5.9b of 3GPP TS 32.422";

      uses types3gpp:PLMNId;
    }

    leaf-list listOfTraceMetrics {
      when 'contains(../jobType, "TRACE")';
      type string;
      description "List of trace metrics identified by name.
        Includes trace messages, MDT measurements (Immediate MDT,
        Logged MDT, Logged MBSFN MDT), RLF, RCEF and RRC reports,
        see TS 32.422. Trace messages are identified with their message
        identifier. Trace metric identifier is constructed as defined
        in clause 10 of TS 32.422.
        For non-3GPP specified trace metrics the name is defined elsewhere.
";
      reference "Clause 10 of 3GPP TS 32.422";
    }

    leaf traceCollectionEntityIPAddress {
      type inet:ip-address;
      description "It specifies the address of the Trace Collection Entity
        when the attribute traceReportingFormat is configured for the
        file-based reporting. The attribute is applicable for both Trace and
        MDT.";
      reference "Clause 5.9 of 3GPP TS 32.422.";
    }


    leaf traceReportingConsumerUri {
      when '../traceReportingFormat  = "STREAMING"';
      type inet:uri;
      description "URI of the Streaming Trace data reporting MnS consumer
        (a.k.a. streaming target).";
      reference "Clause 5.9 of 3GPP TS 32.422.";
    }

    list traceReference {
      key "idx";
      min-elements 1;
      max-elements 1;
      description "A globally unique identifier, which uniquely identifies the
        Trace Session that is created by the TraceJob.
        In case of shared network, it is the MCC and MNC of the Participating
        Operator that request the trace session that shall be provided.
        The attribute is applicable for both Trace and MDT.";
      reference "Clause 5.6 of 3GPP TS 32.422.";

      leaf idx { type uint32 ; }
      uses trace3gpp:TraceReferenceGrp ;
    }

    leaf jobId {
      type string;
      yext3gpp:inVariant;
      description "Identifier of a TraceJob";
    }

    leaf traceReportingFormat {
      type enumeration {
        enum FILE_BASED;
        enum STREAMING;
      }
      default FILE_BASED;
      description "Specifies the trace reporting format - streaming trace
        reporting or file-based trace reporting";
      reference "3GPP TS 32.422 clause 5.11";
    }

    list traceTarget {
      key "traceTargetType";
      max-elements 1;
      description "It specifies the target object of the Trace, MDT and
        5GC UE level measurements collection. The attribute is applicable for
        Trace, MDT, and 5GC UE level measurements collection.
        In case of management based Immediate MDT, RLF reporting, RCEF
        reporting or RRC reposring, the traceTarget attribute shall be null
        value.";

      leaf traceTargetType {
        type enumeration {
          enum IMSI;
          enum IMEI;
          enum IMEISV;
          enum PUBLIC_ID;
          enum UTRAN_CELL;
          enum E_UTRAN_CELL;
          enum NG_RAN_CELL;
          enum ENB;
          enum RNC;
          enum GNB;
          enum SUPI;
          enum N4_SESSION_ID;
        }
        description "It specifies the target object of the Trace, MDT and
          5GC UE level measurements collection. The attribute is applicable for
          Trace, MDT, and 5GC UE level measurements collection.

          The targetIdType shall be PUBLIC_ID in case of a Management Based
          Activation is done to an SCSCFFunction (Serving Call Session Control
          Function) or PCSCFFunction (Proxy Call Session Control Function)

          The targetIdType shall be UTRAN_CELL only in case of
          UTRAN cell traffic trace function.

          The targetIdType shall be E-UTRAN_CELL only in case of E-UTRAN cell
          traffic trace function.

          The targetIdType shall be NG-RAN_CELL only in case of NR cell
          traffic trace function.

          The targetIdType shall be either IMSI, IMEI or
          IMEISV if the Trace Session is activated to any of the following
          ManagedEntity(ies):
          - HssFunction
          - MscServerFunction
          - SgsnFunction
          - GgsnFunction
          - BmscFunction
          - RncFunction
          - MmeFunction
          - ServingGWFunction
          - PGWFunction

          The targetIdType shall be either SUPI or IMEISV if the Trace Session
          is activated to any of the following ManagedEntity(ies):
          - AFFunction
          - AMFFunction
          - AUSFunction
          - NEFFunction
          - NRFFunction
          - NSSFFunction
          - PCFFunction
          - SMFFunction
          - UPFFunction
          - UDMFunction

          In case of signalling based MDT, the targetIdType shall be
          able to carry PUBLIC_ID, IMSI, IMEI, IMEISV or SUPI.

          In case of management based Logged MDT, the targetIdType
          shall carry an eNB or a gNB or an RNC.
          The Logged MDT should be initiated on the specified eNB/gNB/RNC in
          targetIdValueList.

          In case of signalling based 5GC UE level measurements collection,
          the targetIdTypee shall be able to carry IMEISV or SUPI.

          In case of management based 5GC UE level measurements collection,
          the targetIdType shall be able to carry the corresponding
          Measured UE Identifier as defined by the bullet g) of the 5GC UE
          level measurements (see TS 28.558) when the TraceJob is created at
          the subject ManagedEntity.";
      }

      leaf-list traceTargetValueList {
        type string;
        description "It specifies the ID value(s) of the target object defined
          by traceTargetType";
      }

      reference "3GPP TS 32.422";
    }

    list traceConfig {
      when 'contains(../jobType, "TRACE")';
      key idx;
      description "Trace config";
      max-elements 1;
      uses TraceConfigGrp;
      leaf idx { type string; }
    }

    list mdtConfig {
      when 'contains(../jobType, "IMMEDIATE_MDT")'
        + ' or contains(../jobType, "RLF_REPORT_ONLY")'
        + ' or contains(../jobType, "RCEF_REPORT_ONLY")'
        + ' or contains(../jobType, "RRC_REPORT")'
        + ' or contains(../jobType, "LOGGED_MBSFN_MDT")'
        + ' or contains(../jobType, "LOGGED_MDT")';
      key idx;
      description "This <<dataType>> defines the configuration parameters of
        IOC TraceJob which are specific for MDT or any combination of MDT. 
        The attribute anonymizationOfMdtData specifies the level of 
        anonymization of MDT data.
        The optional attribute areaScopedefines the area scope of MDT, which 
        is specified in clause 5.10.2 of TS 32.422.
        The attribute sensorInformation allows to specify the sensor 
        information to include.
        The attribute trsrPrefixCfg contains the TRSR prefix 
        configuration parameters which shall be used by the NR-RAN nodes 
        during TRSR assignment for a C-MDT job.
        Based on the value configured for attribute jobType in IOC TraceJob, 
        the attributes immediateMdtConfig or loggedMdtConfig or both are 
        available: If the attribute jobType indictes immediate MDT, the 
        attribute immediateMdtConfig is applicable. If the attribute jobType 
        indictes logged MDT or logged MBSFN MDT, the attribute loggedMdtConfig
        is applicable. If the attribute jobType indictes both immediate MDT 
        and logged MDT, both the attribute immediateMdtConfig and the 
        attribute loggedMdtConfig are applicable.
        The optional attribute plmnList allows to specify the PLMNs where 
        measurements collection, status indication and log reporting is 
        allowed. For NTN MDT, if the list of plmnList is included, it will 
        only log measurements for the cells belonging to the listed PLMNs.";
      max-elements 1;
      uses MdtConfigGrp;
      leaf idx { type string; }
    }

    list ueCoreMeasConfig {
      when 'contains(../jobType, "5GC_UE_LEVEL_MEASUREMENTS")';
      key idx;
      description "5GC UE level measurements config";
      max-elements 1;
      uses UECoreMeasConfigGrp;
      leaf idx { type string; }
    }

    list nPNTarget {
      description "applicable only for NR and shall be present in case of NPN
        either a PNI-NPN or a SNPN) and for management-based activation when
        several NPNs are supported in the RAN.";
      key idx;
      max-elements 1;
      uses types3gpp:NpnIdGrp;
      leaf idx { type string;}
    }
  }

  grouping TraceSubtree {
    description "Contains classes that manage Tracing.
      Should be used in all  classes (or classes inheriting from)
      - SubNetwork
      - ManagedElement
      - ManagedFunction

      If a YANG module wants to augment these classes/list/groupings they must
      augment all user classes!";

    list TraceJob {
      description "A TraceJob instance represents the Trace Control and
        Configuration parameters of a particular Trace Job (see TS 32.421 and
        TS 32.422 for details). It can be name-contained by SubNetwork,
        ManagedElement, ManagedFunction. In case of signalling based trace 
        activation, it shall be name-contained by the UDMFunction, see TS 28.541.

        To activate Trace Jobs, a MnS consumer has to create TraceJob object
        instances on the MnS producer. A MnS consumer can activate a Trace Job
        for another MnS consumer since it is not required the value of
        traceCollectionEntityIPAddress or traceReportingConsumerUri to be
        his own.

        For the details of Trace Job activation see clauses 4.1.1.1.2 and
        4.1.2.1.2 of TS 32.422.

        When a MnS consumer wishes to deactivate a Trace Job, the MnS consumer
        shall delete the corresponding TraceJob instance. For details of 
        management Trace Job deactivation see clauses 4.1.3.8 to 4.1.3.11 a
        nd 4.1.4.10 to 4.1.4.13  of TS 32.422

        The attribute traceReference specifies a globally unique ID and 
        identifies a Trace session. One Trace Session may be activated to
        multiple Network Elements. The traceReference is populated by the 
        consumer that makes the request for a Trace Session, TS 32.422.
        
        The jobId attribute presents the job identifier of a TraceJob instance.
        The jobId can be used to associate  multiple TraceJob instances.
        For example, it is possible to configure the same jobId value for
        multiple TraceJob instances required to produce the data (e.g. RSRP
        values of M1 and RLF reports) for a specific network analysis.

        The attribute traceReportingFormat defines the method for reporting
        the produced measurements. The selectable options are file-based or
        stream-based reporting. In case of file-based reporting the attribute
        traceCollectionEntityIPAddress is used to specify the IP address to
        which the trace records shall be transferred, while in case of
        stream-based reporting the attribute traceReportingConsumerUri
        specifies the streaming target.

        The attribute traceTarget determines the target object of the 
        TraceJob. Dependent on the network element to which the Trace Session 
        is activated different types of the target object are possible.

        The attribute pLMNTarget defines the PLMN for which sessions shall be 
        selected in the Trace Session in case of management based activation 
        when several PLMNs are supported in the RAN.  The MDT configuration 
        may include area scope defined by network slice, in which case the 
        attribute pLMNTarget is not applicable.

        The attribute listOfTraceMetrics allows configuraton of which metrics
        shall be recorded.

        The attribute jobType specifies the kind of data to collect. In case 
        of TRACE_ONLY, the configuration parameters of attribute traceConfig 
        shall be applied. If the attribute jobType contains IMMEDIATE_MDT, 
        LOGGED_MDT and LOGGED_MBSFN_MDT the configuration parameters of 
        attribute mdtConfig or a subset of these shall be applied. If the 
        attribute jobType contains 5GC_UE_LEVEL_MEASUREMENTS, the configuration
        parameters of attribute ueCoreMeasConfig shall be applied.  

        If jobType has the value RRC_REPORT, the attribute rrcReportType shall
        be present. The rrcReportType allows the tracing of RRC reports.

        Creation and deletion of TraceJob instances by MnS consumers is
        optional; when not supported, the TraceJob instances may be created
        and deleted by the system or be pre-installed.";

      key id;
      uses top3gpp:Top_Grp ;
      container attributes {
        uses TraceJobGrp ;
      }
      uses files3gpp:FilesSubtree {
        if-feature FilesUnderTraceJob;
      }
    }
  }
}
