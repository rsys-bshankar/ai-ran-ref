module _3gpp-nr-nrm-externalgnbcucpfunction {
  yang-version 1.1;
  namespace "urn:3gpp:sa5:_3gpp-nr-nrm-externalgnbcucpfunction";
  prefix "extgnbcucp3gpp";

  import _3gpp-common-yang-types { prefix types3gpp; }
  import _3gpp-common-managed-function { prefix mf3gpp; }
  import _3gpp-common-managed-element { prefix me3gpp; }
  import _3gpp-nr-nrm-gnbcucpfunction { prefix gnbcucp3gpp; }
  import _3gpp-nr-nrm-nrnetwork { prefix nrnet3gpp; }
  import _3gpp-common-subnetwork { prefix subnet3gpp; }
  import _3gpp-nr-nrm-externalnrcellcu { prefix extnrcellcu3gpp; }
  import _3gpp-common-top { prefix top3gpp; }

  organization "3GPP SA5";
  contact "https://www.3gpp.org/DynaReport/TSG-WG--S5--officials.htm?Itemid=464";
  description "Defines the YANG mapping of the ExternalGNBCUCPFunction
    Information Object Class (IOC), that is part of the NR Network Resource
    Model (NRM).
    Copyright 2025, 3GPP Organizational Partners (ARIB, ATIS, CCSA, ETSI, TSDSI, 
    TTA, TTC). All rights reserved.";
  reference "3GPP TS 28.541 5G Network Resource Model (NRM)";

  revision 2025-04-25 { reference "CR-1526 CR-1527" ; } // common for r18, r19
  revision 2023-09-18 { reference CR-1043 ; } 
  revision 2019-10-28 { reference S5-193518 ; }
  revision 2019-06-17 { reference "Initial revision"; }

  grouping ExternalGNBCUCPFunctionGrp {
    description "Represets the ExternalGNBCUCPFunction IOC.";
    uses mf3gpp:ManagedFunctionGrp;

    leaf gNBId {
      description "Identifies a gNB within a PLMN. 
        The gNB ID is part of the NR Cell Identifier (NCI) of the gNB cells.

        See 'gNB Identifier (gNB ID)' of subclause 8.2 of TS 38.300. 
        See 'Global gNB ID' in subclause 9.3.1.6 of TS 38.413";
      mandatory true;
      type uint32 { range "0..4294967295"; }
    }

    leaf gNBIdLength {
      description "Indicates the number of bits for encoding the gNB ID.";
      reference "'Global gNB ID' in subclause 9.3.1.6 of TS 38.413";
      mandatory true;
      type int32 { range "22..32"; }
    }

    list pLMNId {
      description "Specifies the PLMN identifier to be used as part of the
        global RAN node identity.";
      key "mcc mnc";
      min-elements 1;
      max-elements 1;
      uses types3gpp:PLMNId;
    }
  }

  grouping ExternalGNBCUCPFunctionWrapper {
    list ExternalGNBCUCPFunction {
      description "Represents the properties, known by the management function,
        of a GNBCUCPFunction managed by another management function.";
      key id;
      uses top3gpp:Top_Grp;
      container attributes {
        uses ExternalGNBCUCPFunctionGrp;
      }
      uses mf3gpp:ManagedFunctionContainedClasses;
      
      uses extnrcellcu3gpp:ExternalNRCellCUSubtree;
    }
  } 
  
  feature ExternalGNBCUCPFunctionUnderNRNetwork {
    description "The ExternalGNBCUCPFunction shall be contained under
      NRNetwork";
  }
  
  augment "/me3gpp:ManagedElement/gnbcucp3gpp:GNBCUCPFunction/" 
      + "nrnet3gpp:NRNetwork" {
    if-feature ExternalGNBCUCPFunctionUnderNRNetwork;
    uses ExternalGNBCUCPFunctionWrapper;
  }

  feature ExternalGNBCUCPFunctionUnderSubNetwork {
    description "The ExternalGNBCUCPFunction shall be contained under
      SubNetwork";
  }
 
  augment "/subnet3gpp:SubNetwork" {
    if-feature ExternalGNBCUCPFunctionUnderSubNetwork ;
    uses ExternalGNBCUCPFunctionWrapper;
  }
}
