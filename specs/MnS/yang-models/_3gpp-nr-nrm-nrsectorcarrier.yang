module _3gpp-nr-nrm-nrsectorcarrier {
  yang-version 1.1;
  namespace "urn:3gpp:sa5:_3gpp-nr-nrm-nrnetwork-nrsectorcarrier";
  prefix "nrsectcarr3gpp";

  import _3gpp-common-yang-types { prefix types3gpp; }
  import _3gpp-common-managed-function { prefix mf3gpp; }
  import _3gpp-common-managed-element { prefix me3gpp; }
  import _3gpp-nr-nrm-gnbdufunction { prefix gnbdu3gpp; }
  import _3gpp-common-top { prefix top3gpp; }

  organization "3GPP SA5";
  contact "https://www.3gpp.org/DynaReport/TSG-WG--S5--officials.htm?Itemid=464";
  description "Defines the YANG mapping of the NRSectorCarrier Information
    Object Class (IOC) that is part of the NR Network Resource Model (NRM).
    Copyright 2023, 3GPP Organizational Partners (ARIB, ATIS, CCSA, ETSI, TSDSI, 
    TTA, TTC). All rights reserved.";
  reference "3GPP TS 28.541 5G Network Resource Model (NRM)";

  revision 2023-09-18 { reference CR-1043 ; } 
  revision 2020-05-28 { reference CR-0316 ; }
  revision 2019-10-28 { reference S5-193518 ; }
  revision 2019-06-17 {
    description "Initial revision";
  }

  grouping NRSectorCarrierGrp {
    description "Represents the NRSectorCarrier IOC.";
    reference "3GPP TS 28.541";
    uses mf3gpp:ManagedFunctionGrp;

    leaf txDirection {
      description "Indicates if the transmission direction is downlink,
        uplink, or both downlink and uplink.";
      mandatory true;
      type types3gpp:TxDirection;
    }

    leaf configuredMaxTxPower {
      description "Maximum transmisssion power at the antenna port for all 
        downlink channels, used simultaneously in a cell, added together.
        Condition:  The sector-carrier has a downlink and the 
        configuration of Tx power at antenna port reference point is supported.";
      mandatory true;
      type int32;
      units mW;
    }

    leaf configuredMaxTxEIRP {
      type int64;
      units dBm;
      mandatory true;
      description "The maximum emitted isotroptic radiated power (EIRP) in dBm 
        for all downlink channels, used simultaneously in a cell, added together.
        Condition: the sector-carrier has a downlink and the 
        configuration of emitted isotropic radiated power is supported";
    }

    leaf arfcnDL {
      description "NR Absolute Radio Frequency Channel Number (NR-ARFCN)
        for downlink. 
        Condition:  The sector-carrier has a downlink AND the value 
        differs from the referring cell's value of arfcnDL.";
      reference "3GPP TS 38.104";
      mandatory true;
      type int32 { range "0..3279165"; }
    }

    leaf arfcnUL {
      description "NR Absolute Radio Frequency Channel Number (NR-ARFCN)
        for uplink. 
        Condition: The sector-carrier has an uplink AND the value 
        differs from the referring cell's value of arfcnUL.";
      reference "3GPP TS 38.104";
      mandatory true;
      type int32 { range "0..3279165"; }
    }

    leaf bSChannelBwDL {
      description "Base station channel bandwitdth for downlink. 
        Condition: The sector-carrier has a downlink AND the value 
        differs from the referring cell's value of bSChannelBwDL.";
      reference "3GPP TS 38.104";
      mandatory true;
      type int32 { range "5 | 10 | 15 | 20 | 30 | 40 | 50 | 60 | 70 | 80 |
        90 | 100"; }
      units MHz;
    }

    leaf bSChannelBwUL {
      description "Base station channel bandwitdth for uplink.";
      reference "3GPP TS 38.104";
      mandatory true;
      type int32 { range "5 | 10 | 15 | 20 | 30 | 40 | 50 | 60 | 70 | 80 |
        90 | 100"; }
      units MHz;
    }

    leaf sectorEquipmentFunctionRef {
      description "Reference to corresponding SectorEquipmentFunction
        instance.";
      reference "3GPP TS 23.622";
      mandatory true;
      type types3gpp:DistinguishedName;      	
    }		
  }    

  augment "/me3gpp:ManagedElement/gnbdu3gpp:GNBDUFunction" {

    list NRSectorCarrier {
      description "Represents the resources of each transmission point
        included in the cell.";
      reference "3GPP TS 28.541";
      key id;
      uses top3gpp:Top_Grp;
      container attributes {
        uses NRSectorCarrierGrp;
      }
      uses mf3gpp:ManagedFunctionContainedClasses;
    }
  }
}
