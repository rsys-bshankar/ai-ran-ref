module _3gpp-nr-nrm-eutranfrequency {
  yang-version 1.1;
  namespace "urn:3gpp:sa5:_3gpp-nr-nrm-eutranfrequency";
  prefix "eutraneteutranfreq3gpp";

  import _3gpp-common-managed-element { prefix me3gpp; }
  import _3gpp-nr-nrm-gnbcucpfunction { prefix gnbcucp3gpp; }
  import _3gpp-nr-nrm-eutranetwork { prefix eutranet3gpp; }
  import _3gpp-common-subnetwork { prefix subnet3gpp; }
  import _3gpp-common-top { prefix top3gpp; }

  organization "3GPP SA5";
  contact "https://www.3gpp.org/DynaReport/TSG-WG--S5--officials.htm?Itemid=464";
  description "Defines the YANG mapping of the EUtranFrequency Information
    Object Class (IOC), that is part of the NR Network Resource Model (NRM).
    Copyright 2025, 3GPP Organizational Partners (ARIB, ATIS, CCSA, ETSI, TSDSI, 
    TTA, TTC). All rights reserved.";
  reference "3GPP TS 28.541 5G Network Resource Model (NRM),
    3GPP TS 28.658 (E-UTRAN) Network Resource Model (NRM)";

  revision 2025-04-25 { reference "CR-1526 CR-1527" ; } // common for r18, r19
  revision 2023-09-18 { reference CR-1043 ; } 
  revision 2019-10-28 { reference S5-193518 ; }
  revision 2019-06-17 { reference "Initial revision"; }

  grouping EUtranFrequencyGrp {
    description "Represents the EUtranFrequency IOC.";
    reference "3GPP TS 28.541";

    leaf earfcnDL {
      description "Specifies the channel number for the central DL frequency.";
      reference "3GPP TS 36.101";
      mandatory true;
      type uint32 { range "0..262143"; }
    }

    leaf-list multiBandInfoListEutra {
      description "List of additional frequency bands the frequency belongs to.";
      config false;
      min-elements 0;
      type uint16 { range "1..256"; }
    }
  }

  grouping EUtranFrequencyWrapper {
    list EUtranFrequency {
      description "Represents certain E-UTRAN frequency properties.";
      reference "3GPP TS 28.658";
      key id;
      uses top3gpp:Top_Grp;
      container attributes {
        uses EUtranFrequencyGrp;
      }
    }
  } 
  
  feature EUtranFrequencyUnderSubNetwork {
    description "The EUtranFrequency shall be contained under SubNetwork";
  }
  
  augment "/subnet3gpp:SubNetwork" {
    if-feature EUtranFrequencyUnderSubNetwork ;
    uses EUtranFrequencyWrapper;
  }

  feature EUtranFrequencyUnderEUtraNetwork {
    description "The EUtranFrequency shall be contained under EUtraNetwork";
  }
  
  augment "/me3gpp:ManagedElement/gnbcucp3gpp:GNBCUCPFunction/"
        + "eutranet3gpp:EUtraNetwork" {
    if-feature EUtranFrequencyUnderEUtraNetwork;
    uses EUtranFrequencyWrapper;
  }
}
