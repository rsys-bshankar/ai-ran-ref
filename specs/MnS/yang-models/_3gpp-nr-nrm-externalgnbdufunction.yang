module _3gpp-nr-nrm-externalgnbdufunction {
  yang-version 1.1;
  namespace "urn:3gpp:sa5:_3gpp-nr-nrm-externalgnbdufunction";
  prefix "extgnbdu3gpp";

  import _3gpp-common-yang-extensions { prefix yext3gpp; }
  import _3gpp-common-managed-function { prefix mf3gpp; }
  import _3gpp-common-managed-element { prefix me3gpp; }
  import _3gpp-nr-nrm-gnbcucpfunction { prefix gnbcucp3gpp; }
  import _3gpp-nr-nrm-nrnetwork { prefix nrnet3gpp; }
  import _3gpp-common-subnetwork { prefix subnet3gpp; }
  import _3gpp-common-top { prefix top3gpp; }

  organization "3GPP SA5";
  contact "https://www.3gpp.org/DynaReport/TSG-WG--S5--officials.htm?Itemid=464";
  description "Defines the YANG mapping of the ExternalGNBDUFunction
    Information Object Class (IOC) that is part of the NR Network Resource
    Model (NRM).
    Copyright 2025, 3GPP Organizational Partners (ARIB, ATIS, CCSA, ETSI, TSDSI, 
    TTA, TTC). All rights reserved.";
  reference "3GPP TS 28.541 5G Network Resource Model (NRM)";

  revision 2025-04-25 { reference "CR-1526 CR-1527" ; } // common for r18, r19
  revision 2023-09-18 { reference CR-1043 ; } 
  revision 2019-10-28 { reference S5-193518 ; }
  revision 2019-06-17 { reference "Initial revision"; }

  grouping ExternalGNBDUFunctionGrp {
    description "Represets the ExternalGNBDUFunction IOC.";
    reference "3GPP TS 28.541";   
    uses mf3gpp:ManagedFunctionGrp; 
            
    leaf gNBId {
      description "Identifies a gNB within a PLMN. 
        The gNB ID is part of the NR Cell Identifier (NCI) of the gNB cells.

        See 'gNB Identifier (gNB ID)' of subclause 8.2 of TS 38.300. 
        See 'Global gNB ID' in subclause 9.3.1.6 of TS 38.413";
      mandatory true;
      type uint32 { range "0..4294967295"; }
      yext3gpp:inVariant;
    }

    leaf gNBIdLength {
      description "Indicates the number of bits for encoding the gNB ID.";
      reference "'Global gNB ID' in subclause 9.3.1.6 of TS 38.413";
      mandatory true;
      type int32 { range "22..32"; }
    }
  }

  grouping ExternalGNBDUFunctionSubtree {
    list ExternalGNBDUFunction {
      description "Represents the properties, known by the management function,
        of a GNBDUFunction managed by another management function.";
      key id;
      uses top3gpp:Top_Grp;
      container attributes {
        uses ExternalGNBDUFunctionGrp;
      }
      uses mf3gpp:ManagedFunctionContainedClasses;
    }
  } 
  
  feature ExternalGNBDUFunctionUnderNRNetwork {
    description "The ExternalGNBDUFunction shall be contained under
      NRNetwork";
  }
  
  augment "/me3gpp:ManagedElement/gnbcucp3gpp:GNBCUCPFunction/" 
      + "nrnet3gpp:NRNetwork" {
    if-feature ExternalGNBDUFunctionUnderNRNetwork;
    uses ExternalGNBDUFunctionSubtree;
  }

  feature ExternalGNBDUFunctionUnderSubNetwork {
    description "The ExternalGNBDUFunction shall be contained under
      SubNetwork";
  }
 
  augment "/subnet3gpp:SubNetwork" {
    if-feature ExternalGNBDUFunctionUnderSubNetwork ;
    uses ExternalGNBDUFunctionSubtree;
  }
}
