module _3gpp-nr-nrm-nroperatorcelldu {
  yang-version 1.1;
  namespace "urn:3gpp:sa5:_3gpp-nr-nrm-nroperatorcelldu";
  prefix "nropcelld3gpp";

  import _3gpp-common-top { prefix top3gpp; }
  import _3gpp-common-managed-element { prefix me3gpp; }
  import _3gpp-nr-nrm-operatordu { prefix operdu3gpp; }
  import _3gpp-5g-common-yang-types { prefix types5g3gpp; }
  import _3gpp-common-yang-types { prefix types3gpp; }
  import _3gpp-nr-nrm-gnbdufunction { prefix gnbdu3gpp; }
  
  organization "3GPP SA5";
  contact "https://www.3gpp.org/DynaReport/TSG-WG--S5--officials.htm?Itemid=464";
  description "Defines the YANG mapping of the OperatorDU Information Object
    Class (IOC) that is part of the NR Network Resource Model (NRM).
    Copyright 2025, 3GPP Organizational Partners (ARIB, ATIS, CCSA, ETSI, TSDSI, 
    TTA, TTC). All rights reserved.";
  reference "3GPP TS 28.541 5G Network Resource Model (NRM)";

  revision 2025-05-06 { reference "CR-1526 CR-1527" ; }  // common for R18, R19
  revision 2024-05-24 { reference CR-1273 ; } 
  revision 2023-09-18 { reference CR-1043 ; } 
  revision 2021-10-01 { reference "Initial revision"; }

  grouping NROperatorCellDUGrp {
    description "Represents the NROperatorCellDU IOC.";
    reference "3GPP TS 28.541";
    uses operdu3gpp:OperatorDUGrp;
        
    leaf cellLocalId {
      description "Identifies an NR cell of a gNB. Together with the
        corresponding gNB identifier in forms the NR Cell Identity (NCI)."; 
      reference "NCI in 3GPP TS 38.300";
      type int32 { range "0..16383"; }
    }

    leaf administrativeState  {
      description "Administrative state of the NROperatorCellDU. Indicates the
        permission to use or prohibition against using the cell, imposed
        through the OAM services.";
      type types3gpp:AdministrativeState;
      default LOCKED;
    }

    list pLMNInfoList {
      description "The PLMNInfoList is a list of PLMNInfo data type. It 
        defines which PLMNs that can be served by the NR cell, and which 
        S-NSSAIs that can be supported by the NR cell for corresponding PLMN 
        in case of network slicing feature is supported. The plMNId of the 
        first entry of the list is the PLMNId used to construct the nCGI for 
        the NR cell.";
      key "mcc mnc sd sst";
      min-elements 1;
      ordered-by user;
      uses types5g3gpp:PLMNInfo;
    }
    
    leaf nRTAC {
      description "The common 5GS Tracking Area Code for the PLMNs."; 
      reference "3GPP TS 23.003, 3GPP TS 38.473";
      type types5g3gpp:NRTAC;
    }
    
    leaf-list nRCellDURef {
      description "Reference to corresponding NRCellDU instance.";
      type types3gpp:DistinguishedName;
    }

  }

  augment "/me3gpp:ManagedElement/gnbdu3gpp:GNBDUFunction/operdu3gpp:OperatorDU" 
  {

    list NROperatorCellDU {
      description "Contains attributes to support 5G MOCN network sharing.";
      reference "3GPP TS 28.541";
      key id;
      uses top3gpp:Top_Grp;
      container attributes {
        uses NROperatorCellDUGrp;
      }
    }
  }
}
