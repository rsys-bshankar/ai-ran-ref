module _3gpp-nr-nrm-externalamffunction {
  yang-version 1.1;
  namespace "urn:3gpp:sa5:_3gpp-nr-nrm-externalamffunction";
  prefix "extamf3gpp";
    
  import _3gpp-common-managed-function { prefix mf3gpp; }
  import _3gpp-common-subnetwork { prefix subnet3gpp; }
  import _3gpp-common-top { prefix top3gpp; }
  import _3gpp-common-yang-types { prefix types3gpp; }

  organization "3GPP SA5";
  contact "https://www.3gpp.org/DynaReport/TSG-WG--S5--officials.htm?Itemid=464";
  description "Defines the YANG mapping of the ExternalAMFFunction Information
    Object Class (IOC) that is part of the NR Network Resource Model (NRM).
    Copyright 2025, 3GPP Organizational Partners (ARIB, ATIS, CCSA, ETSI, TSDSI, 
    TTA, TTC). All rights reserved.";
  reference "3GPP TS 28.541 5G Network Resource Model (NRM)";

  revision 2025-04-25 { reference "CR-1526 CR-1527" ; } // common for r18, r19
  revision 2023-09-18 { reference CR-1043 ; } 
  revision 2019-10-28 { reference S5-193518 ; }
  revision 2019-06-17 { reference "Initial revision"; }

  grouping ExternalAMFFunctionGrp {
    description "Represents the ExternalAMFFunction IOC.";
    uses mf3gpp:ManagedFunctionGrp;

    list pLMNIdList {
      description "List of at most six entries of PLMN Identifiers, but at least 
        one (the primary PLMN Id).
        The PLMN Identifier is composed of a Mobile Country Code (MCC) and a 
        Mobile Network Code (MNC).";
      min-elements 1;
      max-elements 6;
      key "mcc mnc";
      uses types3gpp:PLMNId;
    }
    
    container aMFIdentifier {
      presence true;
      description "An AMF identifier, comprising an AMF Region ID, an AMF Set ID and an AMF Pointer.";
      uses types3gpp:AmfIdentifier;
    }
  }

  grouping ExternalAMFFunctionWrapper {
    list ExternalAMFFunction {
      description "Represents the properties, known by the management
        function, of a AMFFunction managed by another management
        function.";
      reference "3GPP TS 28.541";
      key id;
      uses top3gpp:Top_Grp;
      container attributes {
        uses ExternalAMFFunctionGrp;
      }
      uses mf3gpp:ManagedFunctionContainedClasses;
    }
  } 
  
  augment "/subnet3gpp:SubNetwork" {
    uses ExternalAMFFunctionWrapper;
  }
}
