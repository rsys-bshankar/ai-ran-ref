module o-ran-cucountgroup{
  yang-version 1.1;
  namespace "urn:o-ran:cucountgroup:1.0";
  prefix "o-ran-cucg";
  

  import _3gpp-common-managed-element { 
    prefix me3gpp; 
  } 
  import _3gpp-nr-nrm-gnbcucpfunction { 
    prefix gnbcucp3gpp; 
  }
  
  organization 
  "O-RAN Alliance";

contact
  "www.o-ran.org";

description 
  "This module defines the YANG definitions for CuCountGroup.

   Copyright 2023 the O-RAN Alliance.

   THIS SOFTWARE IS PROVIDED BY THE COPYRIGHT HOLDERS AND CONTRIBUTORS 'AS IS'
   AND ANY EXPRESS OR IMPLIED WARRANTIES, INCLUDING, BUT NOT LIMITED TO, THE
   IMPLIED WARRANTIES OF MERCHANTABILITY AND FITNESS FOR A PARTICULAR PURPOSE
   ARE DISCLAIMED. IN NO EVENT SHALL THE COPYRIGHT HOLDER OR CONTRIBUTORS BE
   LIABLE FOR ANY DIRECT, INDIRECT, INCIDENTAL, SPECIAL, EXEMPLARY, OR
   CONSEQUENTIAL DAMAGES (INCLUDING, BUT NOT LIMITED TO, PROCUREMENT OF
   SUBSTITUTE GOODS OR SERVICES; LOSS OF USE, DATA, OR PROFITS; OR BUSINESS
   INTERRUPTION) HOWEVER CAUSED AND ON ANY THEORY OF LIABILITY, WHETHER IN
   CONTRACT, STRICT LIABILITY, OR TORT (INCLUDING NEGLIGENCE OR OTHERWISE)
   ARISING IN ANY WAY OUT OF THE USE OF THIS SOFTWARE, EVEN IF ADVISED OF THE
   POSSIBILITY OF SUCH DAMAGE.

   Redistribution and use in source and binary forms, with or without
   modification, are permitted provided that the following conditions are met:

   * Redistributions of source code must retain the above copyright notice,
     this list of conditions and the above disclaimer.
   * Redistributions in binary form must reproduce the above copyright notice,
     this list of conditions and the above disclaimer in the documentation
     and/or other materials provided with the distribution.
   * Neither the Members of the o-RAN Alliance nor the names of its
     contributors may be used to endorse or promote products derived from
     this software without specific prior written permission.";

  revision "2023-03-17" {
    description 
      "version 4.0.0 - first release of this YANG module";

    reference "ORAN-WG5.O-CU-O1-v04.00.docx";
  }
  
  grouping cu-count-groups {
        description
          "cu-count-groups";
    list cu-count-group {
      key "cu-count-group-index";
        description
          "list of cu-count-groups";
      leaf cu-count-group-index {
        type uint8 {
          range 0..30;
        }
        description
          "The attribute provides Cu Counter Group index.";
        }

      leaf-list drb-id {
        type uint8 {
          range 0..32;
        }
        description
          "The attribute provides DRB ID used for concerned CuCountGroup. Value 0 indicates that this DRB ID is not counted in this CuCountGroup.";
      }

      leaf-list qci {
        type uint8 {
          range 0..255;
        }
        description
          "The attribute provides QoS Class Identifier defined in TS 23.401. Logical range and coding specified in TS 23.203. Value 0 indicates that this QCI shall NOT be counted in the CuCountGroup.";
      }

      leaf-list srb-id {
        type uint8 {
          range 0..3;
        }
        description
          "The attribute provides SRB ID used for concerned CuCountGroup. Value 0 indicates that this SRB ID is not counted in this CuCountGroup.";
      }

      leaf-list fiveQi {
        type uint8 {
          range 0..255;
        }
        description
          "The attribute provides 5QI identifier. Value 0 indicates that this 5QI shall NOT be counted in the CuCountGroup.";
      }

      list s-nssai {
        key "sst sd";
        description
          "S-NSSAI as NW Slice identification defined in TS 23.501. If the values of both SD and SST are 0, this slice is not counted in CuCountGroup.";
      leaf sd {
        type uint32 {
          range 0..16777215;
        }
        mandatory true;
        description
          "This parameter indicates the slice differentiator. Value 16777215 (0xFFFFFF) means no SD value associated with the SST.";
        }
        leaf sst {
        type uint8 {
          range 0..255;
        }
        mandatory true;
        description
          "This parameter indicates the slice service type.";
        }
      }
        leaf-list plmn-id {
        type string;
        description
          "3-octet string, representing PLMN Identity";
      }
        leaf-list arp {
        type uint8 {
          range 0..15;
        }
        description
          "This parameter indicates allocation and retention priority. Value 0 indicates that this ARP is not counted in this CuCountGroup.";
      }
    }
  }

  augment "/me3gpp:ManagedElement/gnbcucp3gpp:GNBCUCPFunction/gnbcucp3gpp:attributes" {
    container cu-count-groups {
      uses cu-count-groups;
          description
      "Container of cu-count-groups";
    }
    description
      "Augment of cu-count-groups";
  }

}
