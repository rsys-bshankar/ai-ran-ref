module o-ran-o1-oru {
  yang-version 1.1;
  namespace "urn:o-ran:o-ran-o1-oru";
  prefix "or-oru";

  import _3gpp-common-managed-element { prefix me3gpp; }
  import _3gpp-common-top { prefix top3gpp; }
  import _3gpp-common-yang-types { prefix types3gpp; }
  import _3gpp-common-managed-function { prefix mf3gpp; }

  organization
    "O-RAN Alliance";

  contact
    "www.o-ran.org";

  description
    "Defines the YANG mapping of the ORU Information
     Object Class (IOC) that is part of the O1 NR Network Resource Model (O1NRM).

     Copyright 2026 the O-RAN Alliance.

     THIS SOFTWARE IS PROVIDED BY THE COPYRIGHT HOLDERS AND CONTRIBUTORS 'AS IS'
     AND ANY EXPRESS OR IMPLIED WARRANTIES, INCLUDING, BUT NOT LIMITED TO, THE
     IMPLIED WARRANTIES OF MERCHANTABILITY AND FITNESS FOR A PARTICULAR PURPOSE
     ARE DISCLAIMED. IN NO EVENT SHALL THE COPYRIGHT HOLDER OR CONTRIBUTORS BE
     LIABLE FOR ANY DIRECT, INDIRECT, INCIDENTAL, SPECIAL, EXEMPLARY, OR
     CONSEQUENTIAL DAMAGES (INCLUDING, BUT NOT LIMITED TO, PROCUREMENT OF
     SUBSTITUTE GOODS OR SERVICES; LOSS OF USE, DATA, OR PROFITS; OR BUSINESS
     INTERRUPTION) HOWEVER CAUSED AND ON ANY THEORY OF LIABILITY, WHETHER IN
     CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Redistribution and use in source and binary forms, with or without
     modification, are permitted provided that the following conditions are met:

     * Redistributions of source code must retain the above copyright notice,
     this list of conditions and the above disclaimer.
     * Redistributions in binary form must reproduce the above copyright notice,
     this list of conditions and the above disclaimer in the documentation
     and/or other materials provided with the distribution.
     * Neither the Members of the O-RAN Alliance nor the names of its
     contributors may be used to endorse or promote products derived from
     this software without specific prior written permission.";

  revision 2026-02-11 {
    description
      "Initial version";
    reference "O-RAN.WG10.TS.O1NRM.0-R005-v5.00" ;
  }

  grouping ORUGrp {
    description "Represents the ORU IOC.";
    reference "O-RAN.WG10.TS.O1NRM.0-R005-v5.00";

    leaf ruInstanceId {
      type string;
      description
        "Identifies the O-RU as defined in Open FH M-Plane Specification
         The format is as specified in Open FH M-Plane Interface specification:
         urn:o-ran:operations:1.0:operational-info:declarations:ru-instance-id";
      reference
        "O-RAN.WG4.TS.MP.0-R005-v21.00";
    }

    leaf-list oRUControllerList {
      type string;
      min-elements 1;
      description
        "This attribute contains the DNs of the gNBDUFunction instances with an Open Fronthaul interface to the O-RU.";
      reference
        "O-RAN.WG10.TS.O1NRM.0-R005-v5.00";
    }
  }

  augment "/me3gpp:ManagedElement" {
    description
      "Augmentation name containing ORU under ManagedElement";
    list ORU {
      key id;
      description "Represents the O-RUs defined in Open FH M-Plane Interface";

      reference "O-RAN.WG10.TS.O1NRM.0-R005-v5.00";
      uses top3gpp:Top_Grp;
      container attributes {
        description "Attributes defined by ORU IOC";
        uses ORUGrp;
      }
    }
  }
}
