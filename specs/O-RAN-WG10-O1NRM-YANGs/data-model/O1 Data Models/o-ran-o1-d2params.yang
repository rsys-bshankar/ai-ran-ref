module o-ran-o1-d2params {
  yang-version 1.1;
  namespace "urn:o-ran:o-ran-o1-d2params";
  prefix or-o1-d2params;

  import _3gpp-common-top {
    prefix top3gpp;
  }
  import _3gpp-common-managed-element {
    prefix me3gpp;
  }
  import _3gpp-nr-nrm-gnbdufunction {
    prefix gnbdu3gpp;
  }


  organization
    "O-RAN Alliance";
  contact
    "www.o-ran.org";
  description
    "This module is for O-RAN Work Group 10 O1 Interface Specification for GNB D2 Peer Function

     Copyright 2026 the O-RAN Alliance.

     THIS SOFTWARE IS PROVIDED BY THE COPYRIGHT HOLDERS AND CONTRIBUTORS 'AS IS'
     AND ANY EXPRESS OR IMPLIED WARRANTIES, INCLUDING, BUT NOT LIMITED TO, THE
     IMPLIED WARRANTIES OF MERCHANTABILITY AND FITNESS FOR A PARTICULAR PURPOSE
     ARE DISCLAIMED. IN NO EVENT SHALL THE COPYRIGHT HOLDER OR CONTRIBUTORS BE
     LIABLE FOR ANY DIRECT, INDIRECT, INCIDENTAL, SPECIAL, EXEMPLARY, OR
     CONSEQUENTIAL DAMAGES (INCLUDING, BUT NOT LIMITED TO, PROCUREMENT OF
     SUBSTITUTE GOODS OR SERVICES; LOSS OF USE, DATA, OR PROFITS; OR BUSINESS
     INTERRUPTION) HOWEVER CAUSED AND ON ANY THEORY OF LIABILITY, WHETHER IN
     CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Redistribution and use in source and binary forms, with or without
     modification, are permitted provided that the following conditions are met:

     * Redistributions of source code must retain the above copyright notice,
     this list of conditions and the above disclaimer.
     * Redistributions in binary form must reproduce the above copyright notice,
     this list of conditions and the above disclaimer in the documentation
     and/or other materials provided with the distribution.
     * Neither the Members of the O-RAN Alliance nor the names of its
     contributors may be used to endorse or promote products derived from
     this software without specific prior written permission.";

  revision 2026-01-01 {
    description
      "version 1.0.0

       1) Initial version";
    reference
      "O-RAN.WG10.O1NRM.0-R005-v05.00";
  }


  grouping D2TimingParams {
    description
      "Grouping of Timing information for the O-DUs.";
    leaf t1 {
      type uint32;
      units "microseconds";
      mandatory true;
      description
        "Minimum time for SCell O-DU to
         process and transmit data to a UE once
         data is received from PCell O-DU on
         D2 interface.";
    }
    leaf t2 {
      type uint32;
      units "microseconds";
      mandatory true;
      description
        "Minimum time for PCell O-DU to
         process and respond to DL DATA REQUIRED
         message, and subsequent transmission of
         data in the OTA slot.";
    }
    leaf t3 {
      type uint32;
      units "microseconds";
      mandatory true;
      description
        "Maximum time within which PCell O-DU sends a
         DL SCHEDULING REQUEST message requesting
         scheduling for a given OTA slot.";
    }
  }

 grouping D2ParamsGrp {
    description
      "Represents the D2Params IOC.";

    uses D2TimingParams;
    leaf startCRNTI {
      type uint16 {
        range "1..65522";
      }
      description
        "Defines the start C-RNTI
         assigned to this O-DU.";
    }
    leaf endCRNTI {
      type uint16 {
        range "1..65522";
      }
      description
        "Defines the end C-RNTI
         assigned to this O-DU.";
    }
    leaf-list cellList {
      type int32 {
        range "0..16383";
      }
      min-elements 1;
      description
        "List of cells supported by an O-DU that can
         also support inter O-DU CA via D2 interface.
         It specifies the cell local identifer
         for the cell that supports D2 interface.
         This attribute along with the gNB Identifier
         using gNBId of the parent GNBDUFunction),
         identifies a NR cell within a PLMN.";
    }
    leaf tClearTB {
      type enumeration {
        enum ONE_MS {
          description
            "1 ms duration";
        }
        enum TWO_MS {
          description
            "2 ms duration";
        }
        enum FIVE_MS {
          description
            "5 ms duration";
        }
        enum TEN_MS {
          description
            "10 ms duration";
        }
        enum TWENTY_MS {
          description
            "20 ms duration";
        }
        enum SIXTY_MS {
          description
            "60 ms duration";
        }
      }
      mandatory true;
      description
        "Maximum duration for which the SCell O-DU
         retains the transport Block (TB) for
         retransmission following a HARQ failure";
    }
 }

  augment "/me3gpp:ManagedElement/gnbdu3gpp:GNBDUFunction" {
    description
      "Containment of D2Params IOC under GNBDUFunction.";
    list D2Params {
      key "id";
      max-elements 1;
      description
        "This IOC contains attributes that represent the
         properties of the O-DU supporting D2 interface.";
      uses top3gpp:Top_Grp;
      container attributes {
        description
          "Attributes for management aspects of D2.";
        uses D2ParamsGrp;
      }
    }
  }
}
